Test-Protocol
{ joint-iso-itu-t internationalRA(23) set(42) set-vendors(9) example(99) modules(2) people(2) }

DEFINITIONS IMPLICIT TAGS ::=
BEGIN
IMPORTS
  -- Any of the IMPORTs may be commented out if they are not used (see clause A.3)
  IRI-Parameters,
  IRIsContent
    FROM HI2Operations
    {itu-t(0) identified-organization(4) etsi(0) securityDomain(2) lawfulIntercept(2) hi2(1) version17(17)}
;
    PS-PDU ::= SEQUENCE
    {
       payload Payload
    }
    Payload ::= CHOICE
    {
       optA [0] TypeA,
       eTSI671IRI [1] ETSI671IRI
    }
    TypeA ::= SEQUENCE
    {
       name UTF8String,
       age INTEGER
    }
    TypeB ::= SEQUENCE
    {
       number INTEGER,
       also INTEGER
    }
    ETSI671IRI ::= CHOICE
    {
      stuff  [0] UTF8String,
      iRIsContent   [1] IRIsContent,
      ...
    }   
END


HI2Operations
{itu-t(0) identified-organization(4) etsi(0) securityDomain(2) lawfulIntercept(2) hi2(1) version17(17)}

 -- It is advised not to use version11(11) of this ASN.1 module since it contains a syntax error.
 -- Version11(11) of HI2Operations is only defined in TS 101 671 v3.5.1 [81].

DEFINITIONS IMPLICIT TAGS ::=

BEGIN

IRIsContent ::= CHOICE
{
  iRIContent    IRIContent,
  iRISequence   IRISequence
}

IRISequence ::= SEQUENCE OF IRIContent


IRIContent ::= CHOICE
{
  iRI-Begin-record    [1] IRI-Parameters,
  iRI-End-record      [2] IRI-Parameters,
  iRI-Continue-record   [3] IRI-Parameters,
  iRI-Report-record   [4] IRI-Parameters,
  ...
}

IRI-Parameters ::= SEQUENCE
{
  junk0 [0] UTF8String,
  junk1 [1] INTEGER,
  junk2 [2] PrintableString,
  junk3 [3] UTF8String,
  junk4 [4] INTEGER,
  junk5 [5] PrintableString,
  junk6 [6] UTF8String,
  junk7 [7] INTEGER,
  junk8 [8] PrintableString
}

END
