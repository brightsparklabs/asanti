-- ================================================
-- ETSI Interchange Format (EIF) ASN.1 Syntax
-- ================================================
--
--==== Version History====--
-- Version 1.1.0
--  AD/TICL3 Initial release version 17 March 2013
--     
--
-- Version 1.1.1  (AD/TICL3 130916)
--  Modified National-Parameters definition to include baseStationName and state fields.
--  These fields were created as non-standard tags under the Location definition in the CS ASN.1 schema, as follows
--	antennaBearing		[11]	INTEGER OPTIONAL
--	baseStationName		[12]	OCTET STRING (SIZE (1..50)) OPTIONAL
--	state			[13]	OCTET STRING (SIZE (1..50)) OPTIONAL
--
--  The antennaBearing field from the CS AGF specification is now deprecated by the use of the
--        locationOfTheTarget.gsmLocation.geoCoordinates.azimuth parameter.
--
--
-- Version 1.2.0  (AD/TICL3 140317)
--  Reverted National-Parameters back to the fully ETSI-compliant definition 
--  as an untagged SET SIZE (1..40) OF OCTET STRING (SIZE (1..256))
--  Definitions of the National-Parameters remain the same as per CS ASN.1 schema
--  
--  
-- Version 1.2.2  (AD/TICL3 140331)
--  Updated the national-Parameters section to include YAML-like definitions of national-Parameter elements. 
--  National-Parameters are to be encoded as <key>:<value> pairs.
--  As the national-Parameters are defined as a SET, the artificial (and non-ETSI compliant) requirement
--  that the national-Parameters be presented in a specific order (to facilitate element identification), 
--  which was present in all previous versions of the national-Parameters definition, has now been removed. 
--  
--
-- Version 2.0.2  (D/TICL-ENG 160119)
--  Updated to incorporate latest versions of ETSI 102 232-x specifications and associated ASN.1 schema files
--    TS 102 232-1 v3.10.1 (2015-11) with LI-PS-PDU,ver22.txt
--    TS 102 232-2 v3.8.1 (2014-10) with EmailPDU,ver14.txt
--    TS 102 232-3 v3.3.1 (2013-10) with IPAccessPDU,ver10.txt
--    TS 102 232-4 v3.2.2 (2014-07) with L2AccessPDU,ver7.txt
--    TS 102 232-5 v3.5.1 (2015-10) with IPMultimediaPDU,ver6.txt
--    TS 102 232-6 v3.3.1 (2014-03) with PstnIsdnPDU,ver5.txt
--  
--    TS 133 108 v12.11.0 (2016-01) with UmtsHI2Operations,rel12.txt
--    TS 133 108 v12.11.0 (2016-01) with UmtsCS-HI2Operations,rel12.txt
--    TS 133 108 v12.11.0 (2016-01) with EpsHI2Operations,rel12.txt
--    TS 133 108 v12.11.0 (2016-01) with Umts-HI3-PS,rel12.txt
--    TS 133 108 v12.11.0 (2016-01) with Eps-HI3-PS,rel12.txt
--    TS 133 108 v12.11.0 (2016-01) with ThreeGPP-HI1NotificationOperations,rel12.txt
--
--    TS 101 671 v3.13.1 (2015-11) with HI2Operations,ver18.txt
--    TS 101 671 v3.13.1 (2015-11) with HI1NotificationOperations,ver7.txt
--
--  Changed definition of agencyId within National-HI1-ASN1parameters from VisibleString to IA5String
--  Changed definition of warrantId within National-HI1-ASN1parameters from VisibleString to IA5String
--  Incorporates proposed changes to EmailPDU structure to be submitted to TC LI #41 to accommodate CalDav and CardDav
--
-- Version 2.0.2T  (D/TICL-ENG 160119)
--  Based upon (pure) ETSI version 2.0.2 but modified to accommodate temporary changes in EmailPDU structure for one system (hence the T suffix).
--
--
--========================================================================
--		HEADER SECTION
--========================================================================
-- Source: LI-PS-PDU,ver22.txt
-- ETSI TS 102 232-1 V3.10.1 (2015-11)
-- Annex A.2 ASN.1 specification
LI-PS-PDU
{itu-t(0) identified-organization(4) etsi(0) securityDomain(2) lawfulIntercept(2) li-ps(5) genHeader(1) version22(22)}

DEFINITIONS IMPLICIT TAGS ::=

BEGIN

IMPORTS
	-- Any of the IMPORTs may be commented out if they are not used (see clause A.3)

	-- from TS 101 671 [4]
	LawfulInterceptionIdentifier,
	IRI-Parameters,
	IRIsContent,
	Network-Element-Identifier
		FROM HI2Operations
		{itu-t(0) identified-organization(4) etsi(0) securityDomain(2) lawfulIntercept(2) hi2(1) version18(18)}

	-- from TS 101 671 [4]
	HI1-Operation
		FROM HI1NotificationOperations
		{itu-t(0) identified-organization(4) etsi(0) securityDomain(2) lawfulIntercept(2) hi1(0) notificationOperations(1) version6(6)}

	-- from TS 102 232-02 [5]
	EmailCC,
	EmailIRI,
	MessagingCC,
	MessagingMMCC,
	MessagingIRI
		FROM EmailPDU
		{itu-t(0) identified-organization(4) etsi(0) securityDomain(2) lawfulIntercept(2) li-ps(5) email(2) version14(14)}

	-- from TS 102 232-03 [6]
	IPCC,
	IPIRI,
	IPIRIOnly
		FROM IPAccessPDU
		{itu-t(0) identified-organization(4) etsi(0) securityDomain(2) lawfulIntercept(2) li-ps(5) iPAccess(3) version10(10)}

	-- from TS 102 232-04 [32]
	L2CC,
	L2IRI,
	L2IRIOnly
		FROM L2AccessPDU
		{itu-t(0) identified-organization(4) etsi(0) securityDomain(2) lawfulIntercept(2) li-ps(5) l2Access(4) version7(7)}

	-- from TS 102 232-05 [37]
	IPMMCC,
	IPMMIRI
		FROM IPMultimediaPDU
		{itu-t(0) identified-organization(4) etsi(0) securityDomain(2) lawfulIntercept(2) li-ps(5) iPMultimedia(5) version7(7)}

	-- from TS 102 232-06 [36]
	PstnIsdnCC,
	PstnIsdnIRI
		FROM PstnIsdnPDU
		{itu-t(0) identified-organization(4) etsi(0) securityDomain(2) lawfulIntercept(2) li-ps(5) pstnIsdn(6) version5(5)}

	-- from 3GPP TS 33.108 [9]
	IRI-Parameters,
	UmtsIRIsContent,
	CorrelationValues,
	Location
		FROM UmtsHI2Operations
		{itu-t(0) identified-organization(4) etsi(0) securityDomain(2) lawfulIntercept(2) threeGPP(4) hi2(1)}
			-- The relevant module (including the UMTS release and version number) needs
			-- to be chosen when compiling the application.

	-- from 3GPP TS 33.108 [9]
	IRI-Parameters,
	UmtsCS-IRIsContent
		FROM UmtsCS-HI2Operations
		{itu-t(0) identified-organization(4) etsi(0) securityDomain(2) lawfulIntercept(2) threeGPP(4) hi2CS(3)}
			-- The relevant module (including the UMTS release and version number) needs
			-- to be chosen when compiling the application.

	-- from 3GPP TS 33.108 [9]
	IRI-Parameters,
	EpsIRIsContent,
	EPSLocation
		FROM EpsHI2Operations
		{itu-t(0) identified-organization(4) etsi(0) securityDomain(2) lawfulIntercept(2) threeGPP(4) hi2eps(8)}
			-- The relevant module (including the UMTS release and version number) needs
			-- to be chosen when compiling the application.
	
	-- from 3GPP TS 33.108 [9]
    CC-PDU
        FROM Umts-HI3-PS
        {itu-t(0) identified-organization(4) etsi(0) securityDomain(2) lawfulIntercept(2) threeGPP(4) hi3(2)}
            -- The relevant module (including the UMTS release and version number)
            -- needs to be chosen when compiling the application.

    -- from 3GPP TS 33.108 [9]
    CC-PDU
        FROM Eps-HI3-PS
        {itu-t(0) identified-organization(4) etsi(0) securityDomain(2) lawfulIntercept(2) threeGPP(4) hi3eps(9)}
            -- The relevant module (including the UMTS release and version number)
            -- needs to be chosen when compiling the application.

	-- from 3GPP TS 33.108 [9]
	ThreeGPP-HI1-Operation
        FROM ThreeGPP-HI1NotificationOperations
        {itu-t(0) identified-organization(4) etsi(0) securityDomain(2) lawfulIntercept(2) threeGPP(4) hi1(0) notificationOperations(1)}
            -- The relevant module (including the release and version number)
            -- needs to be chosen when compiling the application. 
			-- TS 101 671 HI1 and 3GPP HI1 are related to the same functionality but are
			-- corresponding to different implementations and exclusive usage each other.
			-- The implementation depends of national regulations or LEA/CSP negotiations. 
			-- 3GPP HI1 may be used with other services/networks than 3GPP’s one.


	-- from TS 101 909-20-1 [33]
	TARGETACTIVITYMONITOR-1,
	TTRAFFIC,
	CTTRAFFIC
		FROM TS101909201
		{itu-t(0) identified-organization(4) etsi(0) ts101909(1909) part20(20) subpart1(1) interceptVersion(0)}

	-- from TS 101 909-20-2 [34]
	TARGETACTIVITYMONITOR,
	TTRAFFIC,
	CTTRAFFIC
		FROM TS101909202
		{itu-t(0) identified-organization(4) etsi(0) ts101909(1909) part20(20) subpart2(2) interceptVersion(0)}

--
-- Begin disable LAESProtocol, CDMA2000LAESMessage, and CCIPPacketHeader as they are not used
--
/*

	-- from J-STD-025-B [39]
	LAESProtocol
		FROM Laesp-j-std-025-b 
		{iso(1) member-body(2) us(840) tia(113737) laes(2) tr45(0) j-std-025(0) j-std-025-b(2) version-1(0)}
	CDMA2000LAESMessage
		FROM CDMA2000CIIModule 
		{iso(1) member-body(2) us(840) tia(113737) laes(2) tr45(0) cdma2000(1) cii(0) version-2(1)}
	CCIPPacketHeader
		FROM CDMA2000CCModule 
		{iso(1) member-body(2) us(840) tia(113737) laes(2) tr45(0) cdma2000(1) cc(1) version-1(0)};

*/
;		
--
-- End disable LAESProtocol, CDMA2000LAESMessage, and CCIPPacketHeader as they are not used
--

-- end of IMPORTS

-- =============================
-- Object Identifier Definitions
-- =============================

lawfulInterceptDomainId OBJECT IDENTIFIER ::= {itu-t(0) identified-organization(4) etsi(0) securityDomain(2) lawfulIntercept(2)}

li-psDomainId OBJECT IDENTIFIER ::= {lawfulInterceptDomainId li-ps(5) genHeader(1) version22(22)}

-- ====================
-- Top-level definition
-- ====================

PS-PDU ::= SEQUENCE
{
	pSHeader	[1] PSHeader,
	payload		[2] Payload
}

PSHeader ::= SEQUENCE
{
	li-psDomainId					[0] OBJECT IDENTIFIER,
	lawfulInterceptionIdentifier	[1] LawfulInterceptionIdentifier,
	authorizationCountryCode		[2] PrintableString (SIZE (2)) OPTIONAL,
		-- see clause 5.2.3
	communicationIdentifier			[3] CommunicationIdentifier, 
	sequenceNumber					[4] INTEGER (0..4294967295),
	timeStamp						[5] GeneralizedTime OPTIONAL,
		-- see clause 5.2.6
	...,
	interceptionPointID				[6] PrintableString (SIZE (1..8)) OPTIONAL,
		-- see clause 5.2.11
	microSecondTimeStamp			[7] MicroSecondTimeStamp OPTIONAL,
	timeStampQualifier				[8] TimeStampQualifier OPTIONAL
}

Payload ::= CHOICE
{
	iRIPayloadSequence		[0] SEQUENCE OF IRIPayload,
	cCPayloadSequence		[1] SEQUENCE OF CCPayload,
		-- Clause 6.2.3 explains how to include more than one payload in the same PDU
	tRIPayload				[2] TRIPayload,
	...,
	hI1-Operation			[3] HI1-Operation,
	encryptionContainer		[4] EncryptionContainer,
	threeGPP-HI1-Operation	[5] ThreeGPP-HI1-Operation
		-- This structure may be functionally redundant with hI1-Operation from TS 101 671

}

TimeStampQualifier ::= ENUMERATED
{
	unknown(0),
	timeOfInterception(1),
	timeOfMediation(2),
	...,
	timeOfAggregation(3)
}

-- ====================================
-- Items contained within the PS-Header
-- ====================================

CommunicationIdentifier ::= SEQUENCE
{
	networkIdentifier				[0] NetworkIdentifier,
	communicationIdentityNumber		[1] INTEGER (0..4294967295) OPTIONAL,
		-- in case of transport of HI1 messages not required
		-- Mandatory for CC and IRI, with certain exceptions (see 5.2.4)
	deliveryCountryCode				[2] PrintableString (SIZE (2)) OPTIONAL,
		-- see clause 5.2.4
	...,
	cINExtension					[3] CorrelationValues OPTIONAL
		-- To be used when a single INTEGER is not sufficient to identify
		-- a particular session (see clause 5.2.4)
}

NetworkIdentifier ::= SEQUENCE
{
	operatorIdentifier			[0] OCTET STRING (SIZE(1..16)),
	networkElementIdentifier	[1] OCTET STRING (SIZE(1..16)) OPTIONAL,
	...,
	eTSI671NEID					[2] Network-Element-Identifier OPTIONAL
		-- For network element identifier, use either networkElementIdentifier or eTSI671NEID
}

-- ==========================
-- Definitions for CC Payload
-- ==========================

CCPayload ::= SEQUENCE
{
	payloadDirection		[0] PayloadDirection OPTIONAL,
	timeStamp				[1] GeneralizedTime OPTIONAL,
		-- For aggregated payloads (see clause 6.2.3)
	cCContents				[2] CCContents,
	...,
	microSecondTimeStamp	[3] MicroSecondTimeStamp OPTIONAL,
		-- For aggregated payloads (see clause 6.2.3)
	timeStampQualifier		[4] TimeStampQualifier OPTIONAL
}

PayloadDirection ::= ENUMERATED
{
	fromTarget(0),
	toTarget(1),
	...,
	indeterminate(2),
		-- Indication that the direction was indeterminate
	combined(3),
		-- Indication applicable to some services that the traffic is actually a combination
		-- of To and From
	notapplicable(4)
		-- Indication that direction of interceptable service does not make sense
}

CCContents ::= CHOICE
	-- Any of these choices may be commented out if they are not being used, see clause A.3
{
	emailCC				[1] EmailCC,
	iPCC				[2] IPCC,
	uMTSCC				[4] OCTET STRING,
	...,
	l2CC				[6] L2CC,
	tTRAFFIC-1			[7] TS101909201.TTRAFFIC,
	cTTRAFFIC-1			[8] TS101909201.CTTRAFFIC,
	tTRAFFIC-2			[9] TS101909202.TTRAFFIC,
	cTTRAFFIC-2			[10] TS101909202.CTTRAFFIC,
	pstnIsdnCC			[11] PstnIsdnCC,
	iPMMCC				[12] IPMMCC,

-- Begin unused.

--	cCIPPacketHeader	[13] CDMA2000CCModule.CCIPPacketHeader,
-- End unused.
	messagingCC			[14] MessagingCC,
	ePSCC				[15] OCTET STRING,
	uMTSCC-CC-PDU		[16] Umts-HI3-PS.CC-PDU,
    ePSCC-CC-PDU		[17] Eps-HI3-PS.CC-PDU,
	messagingMMCC		[18] MessagingMMCC
}

MicroSecondTimeStamp ::= SEQUENCE
{
	seconds			[0] INTEGER (0..18446744073709551615),
		-- number of seconds since 1970-1-1 00:00Z also known as unix time epoch
	microSeconds	[1] INTEGER (0..999999),
	...
}

-- ===========================
-- Definitions for IRI Payload
-- ===========================

IRIPayload ::= SEQUENCE
{
	iRIType			[0] IRIType OPTIONAL,
		-- See clause 5.2.10
	timeStamp		[1] GeneralizedTime OPTIONAL,
		-- For aggregated payloads (see clause 6.2.3)
	iRIContents		[2] IRIContents,
	...,
	microSecondTimeStamp	[3] MicroSecondTimeStamp OPTIONAL,
		-- For aggregated payloads (see clause 6.2.3)
	timeStampQualifier	[4] TimeStampQualifier OPTIONAL,
	sessionDirection	[5] PayloadDirection OPTIONAL,
		-- If the sessionDirection field is to be used for a given service then 
		-- the exact meaning and use of the field will be described in the 
		-- relevant service-specific details
	payloadDirection	[6] PayloadDirection OPTIONAL
		-- If the payloadDirection field is to be used for a given service then 
		-- the exact meaning and use of the field will be described in the 
		-- relevant service-specific details

}

IRIType ::= ENUMERATED
{
	iRI-Begin(1),
	iRI-End(2),
	iRI-Continue(3),
	iRI-Report(4)
}

IRIContents ::= CHOICE
	-- Any of these choices may be commented out if they are not being used (see clause A.3)
{
	emailIRI				[1] EmailIRI,
	iPIRI					[2] IPIRI,
	iPIRIOnly				[3] IPIRIOnly,
	uMTSIRI					[4] UMTSIRI,
	eTSI671IRI				[5] ETSI671IRI,
	...,
	l2IRI					[6] L2IRI,
	l2IRIOnly				[7] L2IRIOnly,
	tARGETACTIVITYMONITOR-1	[8] TS101909201.TARGETACTIVITYMONITOR-1,
	tARGETACTIVITYMONITOR-2	[9] TS101909202.TARGETACTIVITYMONITOR,
	pstnIsdnIRI				[10] PstnIsdnIRI,
	iPMMIRI					[11] IPMMIRI,

-- Begin unused.

--	lAESProtocol			[12] Laesp-j-std-025-b.LAESProtocol,
--	cDMA2000LAESMessage		[13] CDMA2000CIIModule.CDMA2000LAESMessage,
-- End unused.

	messagingIRI			[14] MessagingIRI,
	ePSIRI					[15] EPSIRI
}

UMTSIRI ::= CHOICE
	-- This structure may be commented out if not used
{
	iRI-Parameters		[0] UmtsHI2Operations.IRI-Parameters,
	umtsIRIsContent		[1] UmtsIRIsContent,
	...,
	iRI-CS-Parameters	[2] UmtsCS-HI2Operations.IRI-Parameters,
	umtsCS-IRIsContent	[3] UmtsCS-IRIsContent
}

ETSI671IRI ::= CHOICE
	-- This structure may be commented out if not used
{
	iRI-Parameters	[0] HI2Operations.IRI-Parameters,
	iRIsContent		[1] IRIsContent,
	...
}

EPSIRI ::= CHOICE
	-- This structure may be commented out if not used
{
	iRI-EPS-Parameters	[0] EpsHI2Operations.IRI-Parameters,
	epsIRIsContent		[1] EpsIRIsContent,
	...
}

-- ===========================
-- Definitions for TRI Payload
-- ===========================

TRIPayload ::= CHOICE
{
	integrityCheck					[0] IntegrityCheck,
	testPDU							[1] NULL,
	paddingPDU						[2] OCTET STRING,
		-- Undefined contents (will be discarded)
	keep-alive						[3] NULL,
	keep-aliveResponse				[4] NULL,
	firstSegmentFlag				[5] NULL,
	lastSegmentFlag					[6] NULL,
	...,
	cINReset						[7] NULL,
	operatorLeaMessage				[8] OperatorLeaMessage,
	optionRequest					[9] OptionRequest,
	optionResponse					[10] OptionResponse,
	optionComplete					[11] NULL,
	pDUAcknowledgementRequest		[12] NULL,
	pDUAcknowledgementResponse		[13] NULL
}

IntegrityCheck ::= SEQUENCE
{
	includedSequenceNumbers	[0] SEQUENCE OF INTEGER (0..4294967295),
		-- gives the order the PDUs were processed
	checkType				[1] CheckType,
	dataType				[2] DataType OPTIONAL,
		-- From version5(5) the dataType is mandatory for hashes and for signatures
		-- (see clause 7.2.3)
	checkValue				[3] OCTET STRING,
		-- Network byte order
		-- In case of a DSA/DSS signature, the r and s values shall be concatenated
	...
}

CheckType ::= ENUMERATED
{
	hash(1),
		-- SHA-1 hash value
	signature(2),
		-- DSS/DSA signature
	...
}

DataType ::= ENUMERATED
{
	iRI(1),
	cC(2),
	...
}

Option ::= CHOICE
{
	pDUAcknowledgement	[0] NULL,
	...
}

OptionRequest ::= SEQUENCE
{
	requestedOptions	[0] SEQUENCE OF Option,
	...
}

OptionResponse ::= SEQUENCE
{
	acceptedOptions		[0] SEQUENCE OF Option,
	declinedOptions		[1] SEQUENCE OF Option,
	...
}

-- ==================================
-- Definitions for OperatorLeaMessage
-- ==================================

OperatorLeaMessage ::= SEQUENCE
{
	messagePriority		[0] OperatorLeaMessagePriority,
	message				[1] OCTET STRING (SIZE(1..255)),
	...
}

OperatorLeaMessagePriority ::= ENUMERATED
{
	error(1),
		-- reporting of error conditions that have impact on the quality of the
		-- intercepted data
	informational(2),
		-- reporting of conditions that will not have direct impact on the quality of
		-- the intercepted data
	...
}

-- ===================================
-- Definitions for EncryptionContainer
-- ===================================

EncryptionContainer ::= SEQUENCE
{
	encryptionType			[0] EncryptionType,
	encryptedPayload		[1] OCTET STRING,
		-- once decrypted, it can be interpreted as EncryptedPayload
	...,
	encryptedPayloadType	[2] EncryptedPayloadType OPTIONAL
}

EncryptionType ::= ENUMERATED
{
	none(1),
		-- No encryption is applied.
	national-option(2),
		-- Use this option when an encryption scheme is negotiated on a national level
	aES-192-CBC(3),
		-- The Advanced Encryption Standard using a 192 bit key in CBC mode
	aES-256-CBC(4),
		-- The Advanced Encryption Standard using a 256 bit key in CBC mode
	blowfish-192-CBC(5),
		-- Blowfish (www.schneier.com/blowfish.html) using a 192 bit key in CBC mode
	blowfish-256-CBC(6),
		-- Blowfish using a 256 bit key in CBC mode
	threedes-cbc(7),
		-- Triple-DES using a 192 bit key in CBC mode
	...
}

EncryptedPayload ::= SEQUENCE
{
	byteCounter			[0] INTEGER (0..18446744073709551615),
		-- The sum of the sizes of all PDUs before this PDU.
		-- It is initialized with the unixTime (number of seconds since 01-01-1970)
		-- multiplied by 2^32 at first use.
		-- Where N is sequencenumber of the n-th PDU in transfer, and size(PDU(N))
		-- as defined in annex G:
		-- 		IF N > 0 THEN
		-- 		PDU[N].byteCounter = PDU[N-1].byteCounter + size(PDU[N-1])
		-- 		ELSE
		-- 		PDU[N].byteCounter = ( unixTime(now) << 32 )
		-- 		ENDIF
	payload				[1] Payload,
	...
}

EncryptedPayloadType ::= ENUMERATED
{
	unknown(1),
	part2(2),
		-- encrypted payload is TS 102 232 part 2 [5]
	part3(3),
		-- encrypted payload is TS 102 232 part 3 [6]
	part4(4),
		-- encrypted payload is TS 102 232 part 4 [32]
	part5(5),
		-- encrypted payload is TS 102 232 part 5 [37]
	part6(6),
		-- encrypted payload is TS 102 232 part 6 [36]
	part7(7),
		-- encrypted payload is TS 102 232 part 7 [38]
	...,
	part1(8)
		-- encrypted payload is TS 102 232 part 1 (the present document)
}

-- ==================
-- Common Parameters
-- ==================

Location ::= SEQUENCE
	-- This is a common parameter, the use of this parameter is described in clause 4.5
{
	umtsHI2Location		[0] UmtsHI2Operations.Location OPTIONAL,
	epsLocation		[1] EpsHI2Operations.EPSLocation OPTIONAL,
	...,
	wlanLocationAttributes	[2]	WlanLocationAttributes OPTIONAL

}

WlanLocationAttributes ::= SEQUENCE
{
	wlanAPMACAddress 	[0] OCTET STRING (SIZE(6)) OPTIONAL,
		-- 48-bit (6 octet) MAC address of the WLAN access point derived from the BSSID
	...
} 


END --end of LI-PS-PDU

-- Source: HI2Operations,ver18.txt
-- ETSI TS 101 671 V3.13.1 (2015-11)
-- Annex D.5 Intercept related information (HI2)
HI2Operations
{itu-t(0) identified-organization(4) etsi(0) securityDomain(2) lawfulIntercept(2) hi2(1) version17(18)}

 -- It is advised not to use version11(11) of this ASN.1 module since it contains a syntax error.
 -- Version11(11) of HI2Operations is only defined in TS 101 671 v3.5.1 [81].

DEFINITIONS IMPLICIT TAGS ::=

BEGIN

IMPORTS OPERATION,
	ERROR
		FROM Remote-Operations-Information-Objects
		{joint-iso-itu-t(2) remote-operations(4) informationObjects(5) version1(0)}

	-- from 3GPP TS 33.108 [61]
	UmtsQos,
	IMSevent,
	LDIevent,
	CorrelationValues
		FROM UmtsHI2Operations
		{itu-t(0) identified-organization(4) etsi(0) securityDomain(2) lawfulintercept(2) threeGPP(4) hi2(1) r11(11) version-0(0)}

	-- from TS 101 909-20-01 [69]
	TARGETACTIVITYMONITOR-1
		FROM TS101909201
		{itu-t(0) identified-organization(4) etsi(0) ts101909(1909) part20(20) subpart1(1) interceptVersion(0)}

	-- from EN 301 040 [72]
	TARGETACTIVITYMONITORind,
	TARGETCOMMSMONITORind,
	TTRAFFICind,
	CTTRAFFICind
		FROM EN301040
		{itu-t(0) identified-organization(4) etsi(0) en301040 (1040) interceptVersion (0)};

-- =============================
-- Object Identifier Definitions
-- =============================

-- LawfulIntercept DomainId
lawfulInterceptDomainId OBJECT IDENTIFIER ::= {itu-t(0) identified-organization(4) etsi(0) securityDomain(2) lawfulIntercept(2)}

-- Security Subdomains
hi2DomainId OBJECT IDENTIFIER ::= {lawfulInterceptDomainId hi2(1)}
hi2OperationId OBJECT IDENTIFIER ::= {hi2DomainId version18(18)}

sending-of-IRI OPERATION ::=
{
	ARGUMENT	IRIsContent
	ERRORS		{OperationErrors}
	CODE		global:{hi2DomainId sending-of-IRI(1) version1(1)}
}
-- Class 2 operation. The timer shall be set to a value between 3s and 240s.
-- The timer default value is 60s.
-- NOTE: The same note as for HI management operation applies.

IRIsContent ::= CHOICE
{
	iRIContent		IRIContent,
	iRISequence		IRISequence
}

IRISequence ::= SEQUENCE OF IRIContent
	-- Aggregation of IRIContent is an optional feature.
	-- It may be applied in cases when at a given point in time several IRI records are
	-- available for delivery to the same LEA destination.
	-- As a general rule, records created at any event shall be sent immediately and shall
	-- not held in the DF or MF in order to apply aggregation.
	-- When aggregation is not to be applied, IRIContent needs to be chosen.

IRIContent ::= CHOICE
{
	iRI-Begin-record		[1] IRI-Parameters,
		-- At least one optional parameter must be included within the iRI-Begin-Record.
	iRI-End-record			[2] IRI-Parameters,
	iRI-Continue-record		[3] IRI-Parameters,
		-- At least one optional parameter must be included within the iRI-Continue-Record.
	iRI-Report-record		[4] IRI-Parameters,
		-- At least one optional parameter must be included within the iRI-Report-Record.
	...
}

unknown-version			ERROR ::= {CODE local:0}
missing-parameter		ERROR ::= {CODE local:1}
unknown-parameter-value	ERROR ::= {CODE local:2}
unknown-parameter		ERROR ::= {CODE local:3}

OperationErrors ERROR ::=
{
	unknown-version |
	missing-parameter |
	unknown-parameter-value |
	unknown-parameter
}
-- These values may be sent by the LEMF, when an operation or a parameter is misunderstood.

IRI-Parameters ::= SEQUENCE
{
	domainID							[0]	OBJECT IDENTIFIER (hi2OperationId) OPTIONAL,
		-- for the sending entity the inclusion of the Object Identifier is mandatory
	iRIversion							[23] ENUMERATED
	{
		version2(2),
		...,
		version3(3),
		version4(4),
		version5(5),
		version6(6),
		version7(7),
		lastVersion(8)
	} OPTIONAL,
		-- Optional parameter "iRIversion" (tag 23) is redundant starting
		-- from TS 101 671 v2.5.1 [81]
		-- where to the object identifier "domainID" was introduced into IRI-Parameters.
		-- In order to keep backward compatibility, even when the version of the "domainID"
		-- parameter will be incremented it is recommended to always send to LEMF the same:
		-- enumeration value "lastVersion(8)".
		-- if not present, it means version 1 is handled
	lawfulInterceptionIdentifier		[1] LawfulInterceptionIdentifier,
		-- This identifier is associated to the target.
	communicationIdentifier				[2] CommunicationIdentifier,
		-- used to uniquely identify an intercepted call.
		-- Called "callIdentifier" in v1.1.1 of ES 201 671 [i.5].
	timeStamp							[3] TimeStamp,
		-- date and time of the event triggering the report.
	intercepted-Call-Direct				[4] ENUMERATED
	{
		not-Available(0),
		originating-Target(1),
			-- In case of GPRS, this indicates that the PDP context activation, modification
			-- or deactivation is MS requested.
		terminating-Target(2),
			-- In case of GPRS, this indicates that the PDP context activation, modification
			-- or deactivation is network initiated.
		...
	} OPTIONAL,
	intercepted-Call-State				[5] Intercepted-Call-State OPTIONAL,
	ringingDuration						[6] OCTET STRING (SIZE (3)) OPTIONAL,
		-- Duration in seconds. BCD coded: HHMMSS
	conversationDuration				[7] OCTET STRING (SIZE (3)) OPTIONAL,
		-- Duration in seconds. BCD coded: HHMMSS
	locationOfTheTarget					[8] Location OPTIONAL,
		-- location of the target subscriber
	partyInformation					[9] SET SIZE (1..10) OF PartyInformation OPTIONAL,
		-- This parameter provides the concerned party (Originating, Terminating or forwarded
		-- party), the identity(ies) of the party and all the information provided by the party.
	callContentLinkInformation			[10] SEQUENCE
	{
		cCLink1Characteristics		[1] CallContentLinkCharacteristics OPTIONAL,
			-- Information concerning the Content of Communication Link Tx channel established
			-- toward the LEMF (or the sum signal channel, in case of mono mode).
		cCLink2Characteristics		[2] CallContentLinkCharacteristics OPTIONAL,
			-- Information concerning the Content of Communication Link Rx channel established
			-- toward the LEMF.
		...
	} OPTIONAL,
	release-Reason-Of-Intercepted-Call	[11] OCTET STRING (SIZE (2)) OPTIONAL,
		-- Release cause coded in ITU-T Q.850 [31] format.
		-- This parameter indicates the reason why the intercepted call cannot be established or
		-- why the intercepted call has been released after the active phase.
	nature-Of-The-intercepted-call		[12] ENUMERATED
	{
		-- Nature of the intercepted "call":
		gSM-ISDN-PSTN-circuit-call(0),
			-- the possible UUS content is sent through the HI2 or HI3 "data" interface
			-- the possible call content call is established through the HI3 "circuit" interface
		gSM-SMS-Message(1),
			-- the SMS content is sent through the HI2 or HI3 "data" interface
		uUS4-Messages(2),
			-- the UUS content is sent through the HI2 or HI3 "data" interface
		tETRA-circuit-call(3),
			-- the possible call content call is established through the HI3 "circuit" interface
			-- the possible data are sent through the HI3 "data" interface
		teTRA-Packet-Data(4),
			-- the data are sent through the HI3 "data" interface
		gPRS-Packet-Data(5),
			-- the data are sent through the HI3 "data" interface
		...,
		uMTS-circuit-call(6),
			-- the possible call content call is established through the HI3 "circuit" interface
			-- the possible data are sent through the HI3 "data" interface
		lTE-SMS-Message(7),
			-- indicator for SMS from LTE handset
			-- the SMS content is sent through the HI2 or HI3 "data" interface
		lTE-circuit-call(8)
			-- indicator for CS call from LTE handset
} OPTIONAL,
	serverCenterAddress					[13] PartyInformation OPTIONAL,
		-- e.g. in case of SMS message this parameter provides the address of the relevant
		-- server within the calling (if server is originating) or called
		-- (if server is terminating) party address parameters
	sMS									[14] SMS-report OPTIONAL,
		-- this parameter provides the SMS content and associated information
	cC-Link-Identifier					[15] CC-Link-Identifier OPTIONAL,
		-- Depending on a network option, this parameter may be used to identify a CC link
		-- in case of multiparty calls.
	national-Parameters					[16] National-Parameters OPTIONAL,
	gPRSCorrelationNumber				[18] GPRSCorrelationNumber OPTIONAL,
	gPRSevent							[20] GPRSEvent OPTIONAL,
		-- This information is used to provide particular action of the target
		-- such as attach/detach
	sgsnAddress							[21] DataNodeAddress OPTIONAL,
	gPRSOperationErrorCode				[22] GPRSOperationErrorCode OPTIONAL,
	...,
	ggsnAddress							[24] DataNodeAddress OPTIONAL,
	qOS									[25] UmtsQos OPTIONAL,
		-- This parameter is duplicated from 3GPP TS 33.108 [61].
	networkIdentifier					[26] Network-Identifier OPTIONAL,
		-- This parameter is duplicated from 3GPP TS 33.108 [61].
	sMSOriginatingAddress				[27] DataNodeAddress OPTIONAL,
		-- This parameter is duplicated from 3GPP TS 33.108 [61].
	sMSTerminatingAddress				[28] DataNodeAddress OPTIONAL,
		-- This parameter is duplicated from 3GPP TS 33.108 [61].
	iMSevent							[29] IMSevent OPTIONAL,
	sIPMessage							[30] OCTET STRING OPTIONAL,
		-- This parameter is duplicated from 3GPP TS 33.108 [61].
	servingSGSN-number					[31] OCTET STRING (SIZE (1..20)) OPTIONAL,
		-- This parameter is duplicated from 3GPP TS 33.108 [61].
	servingSGSN-address					[32] OCTET STRING (SIZE (5..17)) OPTIONAL,
		-- Octets are coded according to 3GPP TS 23.003 [76]
		-- This parameter is duplicated from 3GPP TS 33.108 [61].
	tARGETACTIVITYMONITOR				[33] TARGETACTIVITYMONITOR-1 OPTIONAL,
		-- Parameter is used in TS 101 909-20-1 [69]
	ldiEvent							[34] LDIevent OPTIONAL,
		-- The "Location Dependent Interception" parameter is duplicated from 3GPP TS 33.108 [61]
	correlation							[35] CorrelationValues OPTIONAL,
		-- This parameter is duplicated from 3GPP TS 33.108 [61]
	tARGETACTIVITYMONITORind			[36] TARGETACTIVITYMONITORind OPTIONAL,
		-- Parameter is used in EN 301 040 [72]
	tARGETCOMMSMONITORind				[37] TARGETCOMMSMONITORind OPTIONAL,
		-- Parameter is used in EN 301 040 [72]
	tTRAFFICind							[38] TTRAFFICind OPTIONAL,
		-- Parameter is used in EN 301 040 [72]
	cTTRAFFICind						[39] CTTRAFFICind OPTIONAL,
		-- Parameter is used in EN 301 040 [72]
	servingSystem						[40] Network-Element-Identifier OPTIONAL,
		-- Parameter identifies the visited network element
	national-HI2-ASN1parameters			[255] National-HI2-ASN1parameters OPTIONAL
}

-- ==================
-- PARAMETERS FORMATS
-- ==================

CommunicationIdentifier ::= SEQUENCE
{
	communication-Identity-Number	[0] OCTET STRING (SIZE (1..8)) OPTIONAL,
		-- Temporary Identifier of an intercepted call to uniquely identify an intercepted call
		-- within the node. This parameter is mandatory if there is associated
		-- information sent over HI3interface (CClink, data,..) or when
		-- CommunicationIdentifier is used for IRI other than IRI-Report-record
		-- This parameter was called "call-Identity-Number" in V1.1.1 of ES 201 671 [i.5]
		-- The individual digits of the communication-Identity-Number shall be represented in
		-- ASCII format, e.g. "12345678" = 8 octets 0x31 0x32 0x33 0x34 0x35 0x36 0x37 0x38.
		-- For subaddress option only "0"..."9" shall be used.
	network-Identifier				[1] Network-Identifier,
	...
}
-- NOTE: The same "CommunicationIdentifier" value is sent:
-- with the HI3 information for correlation purpose between the IRI and the information sent
-- on the HI3 interfaces (CCLink, data, ..) with each IRI associated to a same intercepted
-- call for correlation purpose between the different IRI.

Network-Identifier ::= SEQUENCE
{
	operator-Identifier			[0] OCTET STRING (SIZE (1..5)),
		-- It is a notification of the NWO/AP/SvP in ASCII- characters.
		-- For subaddress option only "0"..."9" shall be used.
		-- The parameter is mandatory.
	network-Element-Identifier	[1] Network-Element-Identifier OPTIONAL,
	...
}

Network-Element-Identifier ::= CHOICE
{
	e164-Format			[1] OCTET STRING (SIZE (1..25)),
		-- E164 address of the node in international format. Coded in the same format as the
		-- calling party number parameter of the ISUP (parameter part: EN 300 356 [5]).
	x25-Format			[2] OCTET STRING (SIZE (1..25)),
		-- X25 address
	iP-Format			[3] OCTET STRING (SIZE (1..25)),
		-- IP address
	dNS-Format			[4] OCTET STRING (SIZE (1..25)),
		-- DNS address
	...,
	iP-Address			[5] IPAddress
}

CC-Link-Identifier ::= OCTET STRING (SIZE (1..8))
	-- Depending on a network option, this parameter may be used to identify a CClink
	-- in case of multiparty calls.
	-- The individual digits of the CC-Link-Identifier shall be represented in
	-- ASCII format, e.g. "12345678" = 8 octets 0x31 0x32 0x33 0x34 0x35 0x36 0x37 0x38.
	-- For subaddress option only "0"..."9" shall be used.

TimeStamp ::= CHOICE
{
-- The minimum resolution required is one second.
-- "Resolution" is the smallest incremental change that can be measured for time and
-- is expressed with a definite number of decimal digits or bits.
	localTime			[0] LocalTimeStamp,
	utcTime				[1] UTCTime
}

LocalTimeStamp ::= SEQUENCE
{
	generalizedTime					[0] GeneralizedTime,
		-- The minimum resolution required is one second.
		-- "Resolution" is the smallest incremental change that can be measured for time and
		-- is expressed with a definite number of decimal digits or bits.
	winterSummerIndication			[1] ENUMERATED
	{
		notProvided(0),
		winterTime(1),
		summerTime(2),
		...
	}
}

PartyInformation ::= SEQUENCE
{
	party-Qualifier						[0] ENUMERATED
	{
		originating-Party(0),
			-- In this case, the partyInformation parameter provides the identities related to
			-- the originating party and all information provided by this party.
			-- This parameter provides also all the information concerning the redirecting
			-- party when a forwarded call reaches a target.
		terminating-Party(1),
			-- In this case, the partyInformation parameter provides the identities related to
			-- the terminating party and all information provided by this party.
		forwarded-to-Party(2),
			-- In this case, the partyInformation parameter provides the identities related to
			-- the forwarded to party and parties beyond this one and all information
			-- provided by this parties, including the call forwarding reason.
		gPRS-Target(3),
		...
	},
	partyIdentity						[1] SEQUENCE
	{
		imei				[1] OCTET STRING (SIZE (8)) OPTIONAL,
			-- See MAP format TS GSM 09.02 [32]
		tei					[2] OCTET STRING (SIZE (1..15)) OPTIONAL,
			-- ISDN-based Terminal Equipment Identity
		imsi				[3] OCTET STRING (SIZE (3..8)) OPTIONAL,
			-- See MAP format TS GSM 09.02 [32] International Mobile
			-- Station Identity E.212 number beginning with Mobile Country Code
		callingPartyNumber	[4] CallingPartyNumber OPTIONAL,
			-- The calling party format is used to transmit the identity of a calling party
		calledPartyNumber	[5] CalledPartyNumber OPTIONAL,
			-- The called party format is used to transmit the identity of a called party or
			-- a forwarded to party.
		msISDN				[6] OCTET STRING (SIZE (1..9)) OPTIONAL,
			-- MSISDN of the target, encoded in the same format as the AddressString
			-- parameters defined in MAP format TS GSM 09.02 [32]
		...,
		e164-Format			[7] OCTET STRING (SIZE (1..25)) OPTIONAL,
			-- E164 address of the node in international format. Coded in the same format as
			-- the calling party number parameter of the ISUP (parameter part: EN 300 356 [5])
		sip-uri				[8] OCTET STRING OPTIONAL,
			-- Session Initiation Protocol - Uniform Resource Identifier. See RFC 3261 [59].
			-- This parameter is duplicated from 3GPP TS 33.108 [61].
		tel-url				[9] OCTET STRING OPTIONAL,
			-- See "URLs for Telephone Calls", RFC 3966 [68].
			-- This parameter is duplicated from 3GPP TS 33.108 [61].
		party-Validity		[10] ENUMERATED
		{
			trusted(0),
				-- The operator has assured the party identity
			untrusted(1),
				-- The operator does not assure the party identity
			operator-added(2),
				-- The party identity is added by the operator, e.g. the roaming number
			...
		} OPTIONAL,
		alphanumeric	[11] UTF8String OPTIONAL
			-- see clause A.3.3 on usage of this parameter
	},
	services-Information				[2] Services-Information OPTIONAL,
		-- This parameter is used to transmit all the information concerning the
		-- complementary information associated to the basic call
	supplementary-Services-Information	[3] Supplementary-Services OPTIONAL,
		-- This parameter is used to transmit all the information concerning the
		-- activation/invocation of supplementary services during a call or out-of call not
		-- provided by the previous parameters.
	services-Data-Information			[4] Services-Data-Information OPTIONAL,
		-- This parameter is used to transmit all the information concerning the complementary
		-- information associated to the basic data call.
	...
}

CallingPartyNumber ::= CHOICE
{
	iSUP-Format			[1] OCTET STRING (SIZE (1..25)),
		-- Encoded in the same format as the calling party number (parameter field)
		-- of the ISUP (see EN 300 356 [5]).
	dSS1-Format			[2] OCTET STRING (SIZE (1..25)),
		-- Encoded in the format defined for the value part of the Calling party number
		-- information element of DSS1 protocol EN 300 403-1 [6].
		-- The DSS1 Information element identifier and the DSS1 length are not included.
	...,
	mAP-Format			[3] OCTET STRING (SIZE (1..25))
		-- Encoded as AddressString of the MAP protocol TS GSM 09.02 [32].
}

CalledPartyNumber ::= CHOICE
{
	iSUP-Format			[1] OCTET STRING (SIZE (1..25)),
		-- Encoded in the same format as the called party number (parameter field)
		-- of the ISUP (see EN 300 356 [5]).
	mAP-Format			[2] OCTET STRING (SIZE (1..25)),
		-- Encoded as AddressString of the MAP protocol TS GSM 09.02 [32].
	dSS1-Format			[3] OCTET STRING (SIZE (1..25)),
		-- Encoded in the format defined for the value part of the Called party number information
		-- element of DSS1 protocol EN 300 403-1 [6].
		-- The DSS1 Information element identifier and the DSS1 length are not included.
	...
}

Location ::= SEQUENCE
{
	e164-Number			[1] OCTET STRING (SIZE (1..25)) OPTIONAL,
		-- Coded in the same format as the ISUP location number (parameter field)
		-- of the ISUP (see EN 300 356 [5]).
	globalCellID		[2] OCTET STRING (SIZE (5..7)) OPTIONAL,
		-- See MAP format (see TS GSM 09.02 [32]).
	tetraLocation		[3] TetraLocation OPTIONAL,
		-- This optional parameter is not in use anymore, but is kept for backwards compatibility.
	rAI					[4] OCTET STRING (SIZE (6)) OPTIONAL,
		-- The Routeing Area Identifier (RAI) in the current SGSN is coded in accordance with
		-- 3GPP TS 24.008 [41] without the Routing Area Identification IEI (only the
		-- last 6 octets are used).
	gsmLocation			[5] GSMLocation OPTIONAL,
	umtsLocation		[6] UMTSLocation OPTIONAL,
	sAI					[7] OCTET STRING (SIZE (7)) OPTIONAL,
		-- format:	PLMN-ID	3 octets (no. 1-3),
		-- 			LAC		2 octets (no. 4-5),
		-- 			SAC		2 octets (no. 6-7)
		-- 			(according to 3GPP 25.413 [82]).
	...,
	oldRAI				[8] OCTET STRING (SIZE (6)) OPTIONAL,
		-- the "Routeing Area Identifier" in the old SGSN is coded in accordance with
		-- 3GPP TS 24.008 [41] without the Routing Area Identification IEI
		-- (only the last 6 octets are used).
		-- This parameter is duplicated from 3GPP TS 33.108 [61].
	tAI					[9] OCTET STRING (SIZE (6)) OPTIONAL,
		-- The "Tracking Area Identity" (TAI) is coded in accordance with 3GPP TS 29.118 [83] 
		-- without the TAI IEI.
		-- The tAI parameter is applicable only to the CS traffic cases where the available 
		-- location information is the one received from the Mobility Management Entity (MME).
		-- This parameter is duplicated from 3GPP TS 33.108 [61].
	eCGI				[10] OCTET STRING (SIZE (8)) OPTIONAL
		-- the "E-UTRAN Cell Global Identity" (E-CGI) is coded in accordance with 
		-- 3GPP TS 29.118 [83] without the E-CGI IEI.
		-- The eCGI parameter is applicable only to the CS traffic cases where 
		-- the available location information is the one received from the MME.
		-- This parameter is duplicated from 3GPP TS 33.108 [61].
}

TetraLocation ::= CHOICE
	-- This optional parameter is not in use anymore, but is kept for backwards compatibility.
{
	ms-Loc		[1] SEQUENCE
	{
		mcc				[1] INTEGER (0..1023),
			-- 10 bits EN 300 392-1 [40]
		mnc				[2] INTEGER (0..16383),
			-- 14 bits EN 300 392-1 [40]
		lai				[3] INTEGER (0..65535),
			-- 14 bits EN 300 392-1 [40]
		ci				[4] INTEGER OPTIONAL
	},
	ls-Loc		[2] INTEGER
}

GSMLocation ::= CHOICE
{
	geoCoordinates		[1] SEQUENCE
	{
		latitude	[1] PrintableString (SIZE(7..10)),
			-- format: XDDMMSS.SS
		longitude	[2] PrintableString (SIZE(8..11)),
			-- format: XDDDMMSS.SS
		mapDatum	[3] MapDatum DEFAULT wGS84,
		...,
		azimuth		[4] INTEGER (0..359) OPTIONAL
			-- The azimuth is the bearing, relative to true north
	},
		-- format: XDDDMMSS.SS
		-- 		X			: N(orth), S(outh), E(ast), W(est)
		-- 		DD or DDD	: degrees (numeric characters)
		-- 		MM			: minutes (numeric characters)
		-- 		SS.SS		: seconds, the second part (.SS) is optional
		-- Example:
		-- 		latitude short form		N502312
		-- 		longitude long form		E1122312.18

	utmCoordinates		[2] SEQUENCE
	{
		utm-East	[1] PrintableString (SIZE(10)),
		utm-North	[2] PrintableString (SIZE(7)),
			-- Universal Transverse Mercator
			-- example	utm-East	32U0439955
			-- 			utm-North	5540736
		mapDatum	[3] MapDatum DEFAULT wGS84,
		...,
		azimuth		[4] INTEGER (0..359) OPTIONAL
			-- The azimuth is the bearing, relative to true north
	},

	utmRefCoordinates	[3] SEQUENCE
	{
		utmref-string	PrintableString (SIZE(13)),
		mapDatum		MapDatum DEFAULT wGS84,
		...
	},
		-- example 32UPU91294045

	wGS84Coordinates	[4] OCTET STRING
	-- format is as defined in 3GPP TS 03.32 [57]
}

MapDatum ::= ENUMERATED
{
	wGS84,
		-- World Geodetic System 1984
	wGS72,
	eD50,
		-- European Datum 50
	...
}

UMTSLocation ::= CHOICE
{
	point					[1] GA-Point,
	pointWithUnCertainty	[2] GA-PointWithUnCertainty,
	polygon					[3] GA-Polygon,
	...
}

GeographicalCoordinates ::= SEQUENCE
{
	latitudeSign	ENUMERATED
	{
		north,
		south
	},
	latitude		INTEGER (0..8388607),
	longitude		INTEGER (-8388608..8388607),
	...
}

GA-Point ::= SEQUENCE
{
	geographicalCoordinates		GeographicalCoordinates,
	...
}

GA-PointWithUnCertainty ::=SEQUENCE
{
	geographicalCoordinates		GeographicalCoordinates,
	uncertaintyCode				INTEGER (0..127)
}

maxNrOfPoints INTEGER ::= 15

GA-Polygon ::= SEQUENCE (SIZE (1..maxNrOfPoints)) OF
	SEQUENCE
	{
		geographicalCoordinates		GeographicalCoordinates,
		...
	}

CallContentLinkCharacteristics ::= SEQUENCE
{
	cCLink-State			[1] CCLink-State OPTIONAL,
		-- current state of the CCLink
	release-Time			[2] TimeStamp OPTIONAL,
		-- date and time of the release of the Call Content Link.
	release-Reason			[3] OCTET STRING (SIZE(2)) OPTIONAL,
		-- Release cause coded in Q.850 [31] format
	lEMF-Address			[4] CalledPartyNumber OPTIONAL,
		-- Directory number used to route the call toward the LEMF
	...
}

CCLink-State ::= ENUMERATED
{
	setUpInProcess(1),
		-- The set-up of the call is in process
	callActive(2),
	callReleased(3),
	lack-of-resource(4),
		-- The lack-of-resource state is sent when a CC Link cannot
		-- be established because of lack of resource at the MF level.
	...
}

Intercepted-Call-State ::= ENUMERATED
{
	idle(1),
		-- When the intercept call is released, the state is IDLE and the reason is provided
		-- by the release-Reason-Of-Intercepted-Call parameter.
	setUpInProcess(2),
		-- The set-up of the call is in process
	connected(3),
		-- The answer has been received
	...
}

Services-Information ::= SEQUENCE
{
	iSUP-parameters				[1] ISUP-parameters OPTIONAL,
	dSS1-parameters-codeset-0	[2] DSS1-parameters-codeset-0 OPTIONAL,
	...,
	mAP-parameters				[3] MAP-parameters OPTIONAL
}

ISUP-parameters ::= SET SIZE (1..256) OF OCTET STRING (SIZE (1..256))
	-- Each "OCTET STRING" contains one additional ISUP parameter TLV coded not already defined in
	-- the previous parameters. The Tag value is the one given in EN 300 356 [5].

	-- In version 1 of the present document "iSUP-parameters" is defined as mandatory.
	-- It might occur that no ISUP parameter is available. In that case in a version 1
	-- implementation the value "zero" may be included in the first octet string of the SET.

	-- The Length and the Value are coded in accordance with the parameter definition in
	-- EN 300 356 [5]. Hereafter are listed the main parameters.
	-- However other parameters may be added:

	-- Transmission medium requirement: format defined in EN 300 356 [5].
	-- This parameter can be provided with the "Party Information" of the "calling party".

	-- Transmission medium requirement prime: format defined in EN 300 356 [5].
	-- This parameter can be provided with the "Party Information" of the "calling party".

DSS1-parameters-codeset-0 ::= SET SIZE (1..256) OF OCTET STRING (SIZE (1..256))
	-- Each "OCTET STRING" contains one DSS1 parameter of the codeset-0. The parameter is coded as
	-- described in EN 300 403-1 [6] (The DSS1 Information element identifier and the DSS1 length
	-- are included). Hereafter are listed the main parameters.
	-- However other parameters may be added:

	-- Bearer capability: this parameter may be repeated. Format defined in EN 300 403-1 [6].
	-- This parameter can be provided with the "Party Information" of the "calling party",
	-- "called party" or "forwarded to party".

	-- High Layer Compatibility: this parameter may be repeated. Format defined in EN 300 403-1 [6]
	-- This parameter can be provided with the "Party Information" of the "calling party",
	-- "called party" or "forwarded to party".

	-- Low Layer capability: this parameter may be repeated. Format defined in EN 300 403-1 [6].
	-- This parameter can be provided with the "Party Information" of the "calling party",
	-- "called party" or "forwarded to party".

MAP-parameters ::= SET SIZE (1..256) OF OCTET STRING (SIZE(1..256))
	-- Each "OCTET STRING" contains one MAP parameter. The parameter is coded as described in
	-- TS GSM 09.02 [32] (The map-TS-Code is included).

Supplementary-Services ::= SEQUENCE
{
	standard-Supplementary-Services		[1] Standard-Supplementary-Services OPTIONAL,
	non-Standard-Supplementary-Services	[2] Non-Standard-Supplementary-Services OPTIONAL,
	other-Services						[3] Other-Services OPTIONAL,
	...
}

Standard-Supplementary-Services ::= SEQUENCE
{
	iSUP-SS-parameters				[1] ISUP-SS-parameters OPTIONAL,
	dSS1-SS-parameters-codeset-0	[2] DSS1-SS-parameters-codeset-0 OPTIONAL,
	dSS1-SS-parameters-codeset-4	[3] DSS1-SS-parameters-codeset-4 OPTIONAL,
	dSS1-SS-parameters-codeset-5	[4] DSS1-SS-parameters-codeset-5 OPTIONAL,
	dSS1-SS-parameters-codeset-6	[5] DSS1-SS-parameters-codeset-6 OPTIONAL,
	dSS1-SS-parameters-codeset-7	[6] DSS1-SS-parameters-codeset-7 OPTIONAL,
	dSS1-SS-Invoke-components		[7] DSS1-SS-Invoke-Components OPTIONAL,
	mAP-SS-Parameters				[8] MAP-SS-Parameters OPTIONAL,
	mAP-SS-Invoke-Components		[9] MAP-SS-Invoke-Components OPTIONAL,
	...
}

Non-Standard-Supplementary-Services ::= SET SIZE (1..20) OF CHOICE
{
	simpleIndication		[1] SimpleIndication,
	sciData					[2] SciDataMode,
	...
}

Other-Services ::= SET SIZE (1..50) OF OCTET STRING (SIZE (1..256))
	-- Reference manufacturer manuals.

ISUP-SS-parameters ::= SET SIZE (1..256) OF OCTET STRING (SIZE (1..256))
	-- It must be noticed this parameter is retained for compatibility reasons.
	-- It is recommended not to use it in new work but to use ISUP-parameters parameter.

	-- Each "OCTET STRING" contains one additional ISUP parameter TLV coded not already defined in
	-- the previous parameters. The Tag value is the one given in EN 300 356 [5].
	-- The Length and the Value are coded in accordance with the parameter definition in
	-- EN 300 356 [5]. Hereafter are listed the main parameters.
	-- However other parameters may be added:

	-- Connected Number: format defined in EN 300 356 [5].
	-- This parameter can be provided with the "Party Information" of the
	-- "called party" or "forwarded to party".

	-- RedirectingNumber: format defined in EN 300 356 [5].
	-- This parameter can be provided with the "Party Information" of the "originating party"
	-- or/and of the “terminating party”.

	-- Original Called Party Number: format defined in EN 300 356 [5].
	-- This parameter can be provided with the "Party Information" of the "originating party".

	-- Redirection information: format defined in EN 300 356 [5].
	-- This parameter can be provided with the "Party Information" of the
	-- "originating party", "forwarded to party" or/and "Terminating party".

	-- Redirection Number: format defined in EN 300 356 [5].
	-- This parameter can be provided with the "Party Information" of the
	-- "forwarded to party" or "Terminating party".

	-- Call diversion information: format defined in EN 300 356 [5].
	-- This parameter can be provided with the "Party Information" of the
	-- "forwarded to party" or "Terminating party".

	-- Generic Number: format defined in EN 300 356 [5].
	-- This parameter can be provided with the "Party Information" of the
	-- "calling party", "called party" or "forwarded to party".
	-- This parameters are used to transmit additional identities (additional, calling party
	-- number, additional called number, etc.).

	-- Generic Notification: format defined in EN 300 356 [5].
	-- This parameter may be provided with the "Party Information" of the
	-- "calling party", "called party" or "forwarded to party".
	-- This parameters transmit the notification to the other part of the call of the supplementary
	-- services activated or invoked by a subscriber during the call.

	-- CUG Interlock Code: format defined in EN 300 356 [5].
	-- This parameter can be provided with the "Party Information" of the "calling party".

DSS1-SS-parameters-codeset-0 ::= SET SIZE (1..256) OF OCTET STRING (SIZE (1..256))
	-- Each "OCTET STRING" contains one DSS1 parameter of the codeset-0. The parameter is coded as
	-- described in EN 300 403-1 [6] (The DSS1 Information element identifier and the DSS1 length
	-- are included). Hereafter are listed the main parameters.
	-- However other parameters may be added:

	-- Calling Party Subaddress: format defined in EN 300 403-1 [6].
	-- This parameter can be provided with the "Party Information" of the "calling party".

	-- Called Party Subaddress: format defined in EN 300 403-1 [6].
	-- This parameter can be provided with the "Party Information" of the "calling party".

	-- Connected Subaddress: format defined in recommendation (see EN 300 097-1 [14]).
	-- This parameter can be provided with the "Party Information" of the
	-- "called party" or "forwarded to party".

	-- Connected Number: format defined in recommendation (see EN 300 097-1 [14]).
	-- This parameter can be provided with the "Party Information" of the
	-- "called party" or "forwarded to party".

	-- Keypad facility: format defined in EN 300 403-1 [6].
	-- This parameter can be provided with the "Party Information" of the
	-- "calling party", "called party" or "forwarded to party".

	-- Called Party Number: format defined in EN 300 403-1 [6].
	-- This parameter could be provided with the "Party Information" of the "calling party"
	-- when target is the originating party; it contains the dialled digits before modification
	-- at network level (e.g. IN interaction, translation, etc …).

	-- User-user: format defined in EN 300 286-1 [23]).
	-- This parameter can be provided with the "Party Information" of the
	-- "calling party", "called party" or "forwarded to party".

DSS1-SS-parameters-codeset-4 ::= SET SIZE (1..256) OF OCTET STRING (SIZE (1..256))
	-- Each "OCTET STRING" contains one DSS1 parameter of the codeset-4. The parameter is coded as
	-- described in the relevant recommendation.

DSS1-SS-parameters-codeset-5 ::= SET SIZE (1..256) OF OCTET STRING (SIZE (1..256))
	-- Each "OCTET STRING" contains one DSS1 parameter of the codeset-5. The parameter is coded as
	-- described in the relevant national recommendation.

DSS1-SS-parameters-codeset-6 ::= SET SIZE (1..256) OF OCTET STRING (SIZE (1..256))
	-- Each "OCTET STRING" contains one DSS1 parameter of the codeset-6. The parameter is coded as
	-- described in the relevant local network recommendation.

DSS1-SS-parameters-codeset-7 ::= SET SIZE (1..256) OF OCTET STRING (SIZE (1..256))
	-- Each "octet string" contains one DSS1 parameter of the codeset-7. The parameter is coded as
	-- described in the relevant user specific recommendation.

DSS1-SS-Invoke-Components ::= SET SIZE (1..256) OF OCTET STRING (SIZE (1..256))
	-- Each "octet string" contains one DSS1 Invoke or Return Result component.
	-- The invoke or return result component is coded as
	-- described in the relevant DSS1 supplementary service recommendation.

	-- Invoke or Return Result component (BeginCONF): EN 300 185-1 [19]
	-- Invoke or Return Result component (AddCONF): EN 300 185-1 [19]
	-- Invoke or Return Result component (SplitCONF): EN 300 185-1 [19]
	-- Invoke or Return Result component (DropCONF): EN 300 185-1 [19]
	-- Invoke or Return Result component (IsolateCONF): EN 300 185-1 [19]
	-- Invoke or Return Result component (ReattachCONF): EN 300 185-1 [19]
	-- Invoke or Return Result component (PartyDISC): EN 300 185-1 [19]
	-- Invoke or Return Result component (MCIDRequest): EN 300 130-1 [16]
	-- Invoke or Return Result component (Begin3PTY): EN 300 188-1 [20]
	-- Invoke or Return Result component (End3PTY): EN 300 188-1 [20]
	-- Invoke or Return Result component (ECTExecute): EN 300 369-1 [25]
	-- Invoke or Return Result component (ECTInform): EN 300 369-1 [25]
	-- Invoke or Return Result component (ECTLinkIdRequest): EN 300 369-1 [25]
	-- Invoke or Return Result component (ECTLoopTest): EN 300 369-1 [25]
	-- Invoke or Return Result component (ExplicitECTExecute): EN 300 369-1 [25]
	-- Invoke or Return Result component (ECT: RequestSubaddress): EN 300 369-1 [25]
	-- Invoke or Return Result component (ECT: SubaddressTransfer): EN 300 369-1 [25]
	-- Invoke or Return Result component (CF: ActivationDiversion): EN 300 207-1 [21]
	-- Invoke or Return Result component (CF: DeactivationDiversion): EN 300 207-1 [21]
	-- Invoke or Return Result component (CF: ActivationStatusNotification): EN 300 207-1 [21]
	-- Invoke or Return Result component (CF: DeactivationStatusNotification): EN 300 207-1 [21]
	-- Invoke or Return Result component (CF: InterrogationDiversion): EN 300 207-1 [21]
	-- Invoke or Return Result component (CF: InterrogationServedUserNumber): EN 300 207-1 [21]
	-- Invoke or Return Result component (CF: DiversionInformation): EN 300 207-1 [21]
	-- Invoke or Return Result component (CF: CallDeflection): EN 300 207-1 [21]
	-- Invoke or Return Result component (CF: CallRerouteing): EN 300 207-1 [21]
	-- Invoke or Return Result component (CF: DivertingLegInformation1): EN 300 207-1 [21]
	-- Invoke or Return Result component (CF: DivertingLegInformation2): EN 300 207-1 [21]
	-- Invoke or Return Result component (CF: DivertingLegInformation3): EN 300 207-1 [21]
	-- other invoke or return result components ...

MAP-SS-Invoke-Components ::= SET SIZE (1..256) OF OCTET STRING (SIZE (1..256))
	-- Each "octet string" contains one MAP Invoke or Return Result component.
	-- The invoke or return result component is coded as
	-- described in the relevant MAP supplementary service recommendation.

MAP-SS-Parameters ::= SET SIZE (1..256) OF OCTET STRING (SIZE (1..256))
	-- Each "octet string" contains one MAP Parameter. The parameter is coded as
	-- described in the relevant MAP supplementary service recommendation.

SimpleIndication ::= ENUMERATED
{
	call-Waiting-Indication(0),
		-- The target has received a call waiting indication for this call
	add-conf-Indication(1),
		-- this call has been added to a conference
	call-on-hold-Indication(2),
		-- indication that this call is on hold
	retrieve-Indication(3),
		-- indication that this call has been retrieved
	suspend-Indication(4),
		-- indication that this call has been suspended
	resume-Indication(5),
		-- indication that this call has been resumed
	answer-Indication(6),
		-- indication that this call has been answered
	...
}

SciDataMode ::= OCTET STRING (SIZE (1..256))

SMS-report ::= SEQUENCE
{
	communicationIdentifier		[1] CommunicationIdentifier,
		-- used to uniquely identify an intercepted call: the same used for the
		-- relevant IRI
		-- Called "callIdentifier" in V1.1.1 of ES 201 671 [i.5]
	timeStamp					[2] TimeStamp,
		-- date and time of the report. The format is
		-- the one defined in case a) of the ASN.1 ITU-T Recommendation X.680 [33].
		-- (year month day hour minutes seconds)
	sMS-Contents				[3] SEQUENCE
	{
		initiator			[1] ENUMERATED
		{
			-- party which sent the SMS
			target(0),
			server(1),
			undefined-party(2),
			...
		},
		transfer-status		[2] ENUMERATED
		{
			succeed-transfer(0),
				--the transfer of the SMS message succeeds
			not-succeed-transfer(1),
			undefined(2),
			...
		} OPTIONAL,
		other-message		[3] ENUMERATED
		{
			-- In case of terminating call, indicates if the server will send other SMS.
			yes(0),
			no(1),
			undefined(2),
			...
		} OPTIONAL,
		content				[4] OCTET STRING (SIZE (1..270)) OPTIONAL,
			-- Encoded in the format defined for the SMS mobile.
			-- The content and enhancedContent fields are mutually exclusive.
			-- The content field is dedicated for 3GPP purposes.
		...,
		enhancedContent		[5] SEQUENCE
		{
			content				[1] OCTET STRING,
				-- The character encoding used in the content field is specified in the
				-- character-encoding field.
			character-encoding	[2] ENUMERATED
			{
				gsm-7-bit-ascii(0),
				eight-bit-ascii(1),
				eight-bit-binary(2),
				ucs-2(3),
				utf-8(4),
				utf-16(5),
				other(6),
				...
			}
		} OPTIONAL
	}
}

LawfulInterceptionIdentifier ::= OCTET STRING (SIZE (1..25))
	-- It is recommended to use ASCII characters in "a"…"z", "A"…"Z", "-", "_", ".", and "0"…"9".
	-- For subaddress option only "0"..."9" shall be used.

National-Parameters ::= SET SIZE (1..40) OF OCTET STRING (SIZE (1..256))
	-- Content defined by national law.

GPRSCorrelationNumber ::= OCTET STRING (SIZE(8..20))

GPRSEvent ::= ENUMERATED
	-- see 3GPP TS 03.33 [42]
{
	pDPContextActivation(1),
	startOfInterceptionWithPDPContextActive(2),
	pDPContextDeactivation(4),
	gPRSAttach(5),
	gPRSDetach(6),
	cellOrRAUpdate(10),
	sMS(11),
	...,
	pDPContextModification(13),
	endOfInterceptionWithPDPContextActive(14)
}

Services-Data-Information ::= SEQUENCE
{
	gPRS-parameters		[1] GPRS-parameters OPTIONAL,
	...
}

GPRS-parameters ::= SEQUENCE
{
	pDP-address-allocated-to-the-target		[1] DataNodeAddress OPTIONAL,
	aPN										[2] OCTET STRING (SIZE(1..100)) OPTIONAL,
		-- The Access Point Name (APN) is coded in accordance with
		-- 3GPP TS 24.008 [41] without the APN IEI (only the last 100 octets are used).
		-- Octets are coded according to 3GPP TS 23.003 [76].
		-- This parameter is duplicated from 3GPP TS 33.108 [61].
	pDP-type								[3] OCTET STRING (SIZE(2)) OPTIONAL,
		-- when PDP-type is IPv4 or IPv6, the IP address is carried by parameter
		-- pDP-address-allocated-to-the-target when PDP-type is IPv4v6,
		-- the additional IP address is carried by parameter additionalIPaddress
	...,
	nSAPI									[4] OCTET STRING (SIZE (1)) OPTIONAL,
	additionalIPaddress						[5] DataNodeAddress OPTIONAL
}

GPRSOperationErrorCode ::= OCTET STRING (SIZE(2))
	-- Refer to 3GPP TS 24.008 [41] for values (GMM cause or SM cause parameter).

DataNodeAddress ::= CHOICE
{
	ipAddress	[1] IPAddress,
	x25Address	[2] X25Address,
	...
}

IPAddress ::= SEQUENCE
{
	iP-type				[1] ENUMERATED
	{
		iPV4(0),
		iPV6(1),
		...
	},
	iP-value			[2] IP-value,
	iP-assignment		[3] ENUMERATED
	{
		static(1),
			-- The static coding shall be used to report a static address.
		dynamic(2),
			-- The dynamic coding shall be used to report a dynamically allocated address.
		notKnown(3),
			-- The notKnown coding shall be used to report other then static or dynamically
			-- allocated IP addresses.
		...
	} OPTIONAL,
	...,
	iPv6PrefixLength	[4] INTEGER (1..128) OPTIONAL,
		-- Indicates the length of the prefix delegated by the CSP to the subscriber
		-- example: 60 if IP address is “2001:db8:0:85a3::ac1f:8001/60”
		-- Mandatory in case where the iP-value contains an IPv6 binary value
	iPv4SubnetMask		[5] OCTET STRING (SIZE(4)) OPTIONAL
		-- For IPv4 addresses, this indicates the subnetmask to be applied to the iP-value field.
		-- The subnet mask is intended to be presented as a binary value, e.g. "ff ff ff f8" to
		-- represent the dotted-decimal subnet mask of "255.255.255.248" corresponding to
		-- a /29 CIDR-format subnet mask
}

IP-value ::= CHOICE
{
	iPBinaryAddress	[1] OCTET STRING (SIZE(4..16)),
		-- In case of IPv6, the Prefix Length is provided by the "iPv6PrefixLength"
		-- In case of IPv4, the netmask is provided by the "iPv4SubnetMask"
	iPTextAddress	[2] IA5String (SIZE(7..45)),
		-- In case of IPv6, the delivered iPTextAddress field could include a complete
		-- single IPv6-Address or an IPv6-Prefix for a subnetwork on the target side.
		-- In case of IPv4, the delivered iPTextAddress field could include a single
		-- IPv4 address or an IPv4address/netmask, for example "192.168.1.1" or "192.168.1.1/24"
	...
}

X25Address ::= OCTET STRING (SIZE(1..25))

National-HI2-ASN1parameters	::= SEQUENCE
{
	countryCode		[1] PrintableString (SIZE (2)),
		-- Country Code according to ISO 3166-1 [67],
		-- the country to which the parameters inserted after the extension marker apply.
	...
		-- In case a given country wants to use additional national parameters according to its law,
		-- these national parameters should be defined using the ASN.1 syntax and added after the
		-- extension marker (...).
		-- It is recommended that "version parameter" and "vendor identification parameter" are
		-- included in the national parameters definition. Vendor identifications can be
		-- retrieved from the IANA web site (see annex K). Besides, it is recommended to avoid
		-- using tags from 240 to 255 in a formal type definition.
}

END -- end of HI2Operations

-- Source: HI1NotificationOperations,ver7.txt
-- ETSI TS 101 671 V3.13.1 (2015-11)
-- Annex D.4 LI management notification
HI1NotificationOperations
{itu-t(0) identified-organization(4) etsi(0) securityDomain(2) lawfulIntercept(2) hi1(0) notificationOperations(1) version7(7)}

DEFINITIONS IMPLICIT TAGS ::=
BEGIN

IMPORTS
	OPERATION,
	ERROR
		FROM Remote-Operations-Information-Objects
		{joint-iso-itu-t(2) remote-operations(4) informationObjects(5) version1(0)}

	-- from clause D.5
	CommunicationIdentifier,
	TimeStamp,
	LawfulInterceptionIdentifier
		FROM HI2Operations
		{itu-t(0) identified-organization(4) etsi(0) securityDomain(2) lawfulIntercept(2) hi2(1) version10(10)};

-- =============================
-- Object Identifier Definitions
-- =============================

-- LawfulIntercept DomainId
lawfulInterceptDomainId OBJECT IDENTIFIER ::= {itu-t(0) identified-organization(4) etsi(0) securityDomain(2) lawfulIntercept(2)}

-- hi1 Domain
hi1NotificationOperationsId OBJECT IDENTIFIER ::= {lawfulInterceptDomainId hi1(0) notificationOperations(1)}
hi1OperationId OBJECT IDENTIFIER ::= {hi1NotificationOperationsId version6(6)}

sending-of-HI1-Notification 	OPERATION ::=
{
	ARGUMENT	HI1-Operation
	ERRORS		{ErrorHI1Notifications}
	CODE		global:{hi1NotificationOperationsId version1(1)}
}
-- Class 2 operation. The timer shall be set to a value between 3s and 240s.
-- The timer default value is 60s.
-- NOTE: The value for this timer is to be set on the equipment waiting for the returned message;
-- its value shall be agreed between the NWO/AP/SvP and the LEA, depending on their equipment
-- properties.

other-failure-causes 	ERROR ::= {CODE local:0}
missing-parameter		ERROR ::= {CODE local:1}
unknown-parameter		ERROR ::= {CODE local:2}
erroneous-parameter		ERROR ::= {CODE local:3}

ErrorHI1Notifications ERROR ::=
{
	other-failure-causes |
	missing-parameter |
	unknown-parameter |
	erroneous-parameter
}

HI1-Operation 	::= CHOICE
{
	liActivated						[1] Notification,
	liDeactivated					[2] Notification,
	liModified						[3] Notification,
	alarms-indicator				[4] Alarm-Indicator,
	...,
	national-HI1-ASN1parameters		[5] National-HI1-ASN1parameters
}

-- ==================
-- PARAMETERS FORMATS
-- ==================

Notification 	::= SEQUENCE
{
	domainID						[0] OBJECT IDENTIFIER (hi1OperationId) OPTIONAL,
		-- Once using FTP delivery mechanism
	lawfulInterceptionIdentifier 	[1] LawfulInterceptionIdentifier,
		-- This identifier is the LIID identity provided with the lawful authorization
		-- for each target.
	communicationIdentifier 		[2] CommunicationIdentifier OPTIONAL,
		-- Only the NWO/PA/SvPIdentifier is provided (the one provided with the Lawful
		-- authorization).
		-- Called "callIdentifier" in V1.1.1 of ES 201 671
	timeStamp						[3] TimeStamp,
		-- date and time of the report.
	...,
	national-HI1-ASN1parameters		[5] National-HI1-ASN1parameters OPTIONAL,
	target-Information				[6] OCTET STRING (SIZE (1..256)) OPTIONAL
		-- provides information about the number or the characteristic of the target 
		-- (e.g. E-mail address, E.164 number), ASCII format
}

Alarm-Indicator 	::= SEQUENCE
{
	domainID						[0] OBJECT IDENTIFIER (hi1OperationId) OPTIONAL,
		-- Once using FTP delivery mechanism
	communicationIdentifier					[1] CommunicationIdentifier OPTIONAL,
		-- Only the NWO/PA/SvPIdentifier is provided (the one provided with the
		-- Lawful authorization)
	timeStamp						[2] TimeStamp,
		-- date and time of the report.
	alarm-information					[3] OCTET STRING (SIZE (1..256)),
		-- Provides information about alarms (free format).
		-- Until ASN.1 version 6 (document version v3.12.1) the octet string
		-- was limited to a size of 25
	...,
	lawfulInterceptionIdentifier				[4] LawfulInterceptionIdentifier OPTIONAL,
		-- This identifier is the LIID identity provided with the lawful authorization
		-- for each target in according to national law.
	national-HI1-ASN1parameters				[5] National-HI1-ASN1parameters OPTIONAL
}

National-HI1-ASN1parameters		::= SEQUENCE
{
	domainID		[0] OBJECT IDENTIFIER (hi1OperationId) OPTIONAL,
		-- Once using FTP delivery mechanism.
	countryCode		[1] PrintableString (SIZE (2)),
		-- Country Code according to ISO 3166-1 [67],
		-- the country to which the parameters inserted after the extension marker apply.
	...
		-- In case a given country wants to use additional national parameters according to its law,
		-- these national parameters should be defined using the ASN.1 syntax and added after the
		-- extension marker (...).
		-- It is recommended that "version parameter" and "vendor identification parameter" are
		-- included in the national parameters definition. Vendor identifications can be
		-- retrieved from IANA web site (see annex K). Besides, it is recommended to avoid
		-- using tags from 240 to 255 in a formal type definition.

--
-- Begin National HI1 parameter extension for Australia.
--
-- Added per Consolidated Specification, Sections 20.4 and 20.5 (Draft release 1.1.3, date 19/01/16).
-- countryCode must be set to "AU" for these extensions to be valid.
--
	,
	version			[2] ENUMERATED
	{
		version1(1),
		...
	} OPTIONAL,
	interceptType		[3] ENUMERATED
	{
		iRIandCC (0),
		iRIonly (1),
		...
	} OPTIONAL,
	agencyID		[4] IA5String (SIZE (1..256)) OPTIONAL,
	warrantID		[5] IA5String (SIZE (1..256)) OPTIONAL
--
-- End National HI1 parameter extension for Australia.
--
}
END -- end of HI1NotificationOperations




-- Source: EmailPDU,ver14.txt
-- ETSI TS 102 232-2 V3.8.1 (2014-10)
-- Annex D (normative): E-mail ASN.1
-- Also includes changes proposed (but as yet un-ratified by ETSI) for Email and Messaging (D/TICL-ENG 20151020)

EmailPDU
{itu-t(0) identified-organization(4) etsi(0) securityDomain(2) lawfulIntercept(2) li-ps(5) email(2) version14(14)}
DEFINITIONS IMPLICIT TAGS ::=
BEGIN
IMPORTS
-- from TS 101 671 [4]
	IPAddress
		FROM HI2Operations
		{itu-t(0) identified-organization(4) etsi(0) securityDomain(2) lawfulIntercept(2) hi2(1) version18(18)}
-- from TS 102 232-5 [38]
	IPMMCC
		FROM IPMultimediaPDU
		{itu-t(0) identified-organization(4) etsi(0) securityDomain(2) lawfulIntercept(2) li-ps(5) iPMultimedia(5) version6(6)};
-- ============================
-- Object Identifier Definition
-- ============================
emailIRIObjId RELATIVE-OID		::= {li-ps(5) email(2) version14(14) iRI(1)}
emailCCObjId RELATIVE-OID		::= {li-ps(5) email(2) version14(14) cC(2)}
messagingIRIObjId RELATIVE-OID 	::= {li-ps(5) email(2) version14(14) messagingIRI(3)}
messagingCCObjId RELATIVE-OID 	::= {li-ps(5) email(2) version14(14) messagingCC(4)}
messagingMMCCObjId RELATIVE-OID	::= {li-ps(5) email(2) version14(14) messagingMMCC(5)}
-- definitions are relative to 
-- {itu-t(0) identified-organization(4) etsi(0) securityDomain(2) lawfulintercept(2)}
-- =============================
-- Email Communications Contents
-- =============================
EmailCC ::= SEQUENCE
-- EmailCC is the PDU sent for each "piece" of E-mail captured content
{
	emailCCObjId		[0] RELATIVE-OID,
	email-Format		[1] Email-Format,
	content				[2] OCTET STRING,
-- Network byte order
	...,
	content-type				[3] OCTET STRING,
-- MIME content type, i.e.: image/png, text/plain;charset=utf8, audio/PCMA
	event-identifier			[4] INTEGER (0..4294967295),
-- Used to correlate EmailCC to EmailIRI within the same CIN
	content-identifier			[5] INTEGER (0..4294967295) OPTIONAL,
	sequence-number				[6] INTEGER (0..4294967295) OPTIONAL,
	end-of-sequence				[7] BOOLEAN DEFAULT FALSE
}
Email-Format ::= ENUMERATED
{
	ip-packet(1),
-- When this is the email format, the content will contain the bytes of the IP packet from 
-- the IP header through to the end of the IP packet
-- Meets requirement E.2.7
	application(2)
-- Only the IP stack Layer 4 payload, (i.e. no IP or TCP headers)
-- Meets requirement E.2.8
}
-- =======================================
-- Intercept-related information for Email
-- =======================================
EmailIRI ::= SEQUENCE
-- EmailIRI is the PDU sent for each "piece" of E-mail IRI
{
	emailIRIObjId				[0] RELATIVE-OID,
	eventType					[1] E-mail-Event,
	client-Address				[2] IPAddress OPTIONAL,
-- Provided if available
	server-Address				[3] IPAddress OPTIONAL,
-- Provided if available
	client-Port					[4] INTEGER OPTIONAL,
-- Provided if available
	server-Port					[5] INTEGER OPTIONAL,
-- Provided if available
	server-Octets-Sent			[6] INTEGER,
	client-Octets-Sent			[7] INTEGER,
	protocol-ID					[8] E-mail-Protocol,
	e-mail-Sender				[9] UTF8String (SIZE (0..255)) OPTIONAL,
-- Not available in some cases; if a value is available, it must be provided
	e-mail-Recipients			[10] E-mail-Address-List OPTIONAL,
-- Not available in some cases; if a value is available, it must be provided
	status						[11] E-mail-Status,
	total-Recipient-Count 		[12] INTEGER (0..4294967295) OPTIONAL,
	message-ID					[13] OCTET STRING OPTIONAL,
-- Network byte order
	nationalParameter			[14] OCTET STRING OPTIONAL,
-- Completely defined on a national basis, including byte ordering
	...,
	national-EM-ASN1parameters	[15] National-EM-ASN1parameters OPTIONAL,
-- Completely defined on a national basis
	aAAInformation				[16] AAAInformation OPTIONAL,
	e-mail-Sender-Validity		[17] ENUMERATED
		{
			validated(0),
-- The operator has assured the e-mail-sender
			nonvalidated(1),
-- The operator does not assure the e-mail-sender
			...
		} OPTIONAL,
	event-identifier			[18] INTEGER (0..4294967295) OPTIONAL
-- Used to correlate EmailIRI to EmailCC within the same CIN. 
-- Mandatory when EmailCC is also sent.
}
E-mail-Status ::= ENUMERATED
{
	status-unknown(1),
	operation-failed(2),
	operation-succeeded(3)
}
E-mail-Event ::= ENUMERATED
{
	e-mail-send(1),
	e-mail-receive(2),
	e-mail-download(3),
	...,
	e-mail-logon-attempt(4),
	e-mail-logon(5),
	e-mail-logon-failure(6),
	e-mail-logoff(7),
	e-mail-partial-download(8),
	e-mail-upload(9),
	e-mail-draft-deposit(10)
}
E-mail-Protocol ::= ENUMERATED
{
	smtp(1),
	pop3(2),
	imap4(3),
	webmail(4),
-- See Annex H for more information
	undefined(255),
-- The protocol is not known or not representable by the current enumeration
	...
}
E-mail-Address-List ::= SEQUENCE (SIZE (0..1023)) OF UTF8String(SIZE (0..255))
National-EM-ASN1parameters ::= SEQUENCE
{
	countryCode		[1] PrintableString (SIZE (2)),
-- Country Code according to ISO 3166-1 [12],
-- the country to which the parameters inserted after the extension marker apply
	...
-- In case a given country wants to use additional national parameters according to its law,
-- these national parameters should be defined using the ASN.1 syntax and added after the 
-- extension marker (...)
}
AAAInformation ::= CHOICE
-- The AAAInformation field allows for POP3 and authenticated SMTP AAA information
{
	pOP3AAAInformation			[0] POP3AAAInformation,
	aSMTPAAAInformation			[1] ASMTPAAAInformation,
	...,
	iMAPAAAInformation			[2] IMAPAAAInformation,
	hTTPAAAInformation			[3] HTTPAAAInformation
}
POP3AAAInformation ::= SEQUENCE
-- The POP3AAAInformation field contains the POP3 username & optionally the password
{
	username					[0] UTF8String (SIZE (0..64)),
	password					[1] UTF8String (SIZE (0..64)) OPTIONAL,
	aAAResult					[2] AAAResult OPTIONAL,
	...
}
ASMTPAAAInformation ::= SEQUENCE
-- The ASMTPAAAInformation field contains the SMTP username and
-- optionally the authentication fields
{
	username					[0] UTF8String (SIZE (0..64)),
	authMethod					[1] AAAauthMethod OPTIONAL,
-- The hashing method used, i.e. CRAM-MD5, DIGEST-MD5, etc
	challenge					[2] OCTET STRING OPTIONAL,
-- A BASE64 encoded challenge send by the SMTP server
	response					[3] OCTET STRING OPTIONAL,
-- A BASE64 encoded hashed response returned by the client
	aAAResult					[4] AAAResult OPTIONAL,
	...
}
IMAPAAAInformation ::= SEQUENCE
-- The iMAPAAAInformation field contains the IMAP username & optionally the password
{
	username					[0] UTF8String (SIZE (0..64)),
	password					[1] UTF8String (SIZE (0..64)) OPTIONAL,
	aAAResult					[2] AAAResult OPTIONAL,
	...
}
HTTPAAAInformation ::= SEQUENCE
-- The HTTPAAAInformation field contains authentication information for Webmail and for any HTTP/S services (eg CardDav and CalDav)
{
	username					[0] UTF8String (SIZE (0..64)) OPTIONAL,
	password					[1] UTF8String (SIZE (0..64)) OPTIONAL,
	rawAAAData			 		[3] OCTET STRING OPTIONAL,
-- Content of the raw AAA record
	...
}
AAAResult ::= ENUMERATED
{
	resultUnknown(1),
	aAAFailed(2),
	aAASucceeded(3),
	...
}
AAAauthMethod ::= ENUMERATED
{
	undefinedAuthMethod(1),
	cramMD5(2),
	digestMD5(3),
	...
}
-- =================================
-- Messaging Communications Contents
-- =================================
MessagingCC ::= SEQUENCE
-- MessagingCC is the PDU sent for the captured content
{
	messaging-cc-obj-id			[0] RELATIVE-OID,
	event-identifier			[1] INTEGER (0..4294967295),
-- Used to correlate to MessagingIRI within the same CIN
	content-identifier			[2] INTEGER (0..4294967295) OPTIONAL,
	sequence-number				[3] INTEGER (0..4294967295) OPTIONAL,
	end-of-sequence				[4] BOOLEAN DEFAULT FALSE,
	content-type				[5] OCTET STRING,
-- MIME content type, i.e.: image/png, text/plain;charset=utf8, audio/PCMA
	content						[6] OCTET STRING,
	...,
	content-transfer-encoding	[7] OCTET STRING OPTIONAL
-- MIME Content-Transfer-Encoding mechanism.
-- Refer to IETF RFC 2045 [20]
}
MessagingMMCC ::= SEQUENCE
-- MessagingMMCC is the PDU sent for the captured IPMMCC content
{
	messaging-mm-cc-obj-id		[0] RELATIVE-OID,
	event-identifier			[1] INTEGER (0..4294967295),
-- Used to correlate to MessagingIRI within the same CIN
	content-identifier			[2] INTEGER (0..4294967295) OPTIONAL,
	content						[3] IPMMCC,
	...
}
-- ===========================================
-- Intercept-related information for Messaging
-- ===========================================
MessagingIRI ::= SEQUENCE
{
	messaging-iri-obj-id		[0] RELATIVE-OID,
	system-type					[1] Messaging-System-Type,
	system-identifier			[2] OCTET STRING OPTIONAL,
-- Identifier up to national agreement, uniquely identifies a certain messaging system
	category					[3] Messaging-Event-Category OPTIONAL,
	status						[4] Messaging-Status,
	party-information			[5] SET OF Messaging-Party-Information OPTIONAL,
	trigger						[6] Messaging-Trigger,
	properties					[7] SEQUENCE OF Messaging-Property OPTIONAL,
	event-identifier			[8] INTEGER (0..4294967295) OPTIONAL,
-- Used to correlate to MessagingCC or MessagingMMCC within the same CIN. Mandatory when CC is also sent
	original-message			[9] OCTET STRING OPTIONAL,
	...,
	box-identifier				[10] OCTET STRING OPTIONAL
}
Messaging-System-Type ::= ENUMERATED
{
	unified-messaging(1),
	...
}
Messaging-Event-Category ::= CHOICE
{
	message						[0] Messaging-Event,
	message-box					[1] Messaging-Box-Event,
	message-notification		[2] Messaging-Notification-Event,
	call						[3] Messaging-Call-Event,
	...
}
Messaging-Event ::= ENUMERATED
{
	deposit(1),
	retrieve(2),
	delete(3),
	save(4),
	slamdown(5),
	...
}
Messaging-Box-Event ::= ENUMERATED
{
	login(1),
	logout(2),
	lock(3),
	unlock(4),
	activate(5),
	deactivate(6),
	delete(7),
	pin-change(8),
	greeting-record(9),
	greeting-change(10),
	greeting-delete(11),
	greeting-enable(12),
	greeting-disable(13),
	notification-enable(14),
	notification-disable(15),
	disconnect(16),
	connect(17),
	...,
	--unknown(0),
	greeting-play(18),
	language-change(19),
	pin-security-enable(20),
	pin-security-disable(21),
	personal-operator-add(22),
	personal-operator-change(23),
--	personal-operator-remove(24),
	additional-destination-add(25),
	additional-destination-change(26),
	additional-destination-remove(27),
	personal-operator-remove(250),  		-- Carrier-specific temporary implementation (MH)
	personal-operator-number-change(251),  	-- Carrier-specific temporary implementation (MH)
	additional-ids-add(252),  				-- Carrier-specific temporary implementation (MH)
	additional-ids-change(253),  			-- Carrier-specific temporary implementation (MH)
	additional-ids-remove(254)  			-- Carrier-specific temporary implementation (MH)
}
Messaging-Notification-Event ::= ENUMERATED
{
	sms(1),
	sms-deposit(2),
	sms-slamdown(3),
	sms-pin-reminder(4),
	email(5),
	fax-to-email(6),
	...,
	mms(7),
	generic(8),
	calendar(9),
	contact(10),
	message-wait-indication(254)  			-- Carrier-specific temporary implementation (MH)
}
Messaging-Call-Event ::= ENUMERATED
{
	callout(1),
	...
}
Messaging-Status ::= ENUMERATED
{
	unknown(0),
	not-applicable(1),
	operation-failed(2),
	operation-succeeded(3),
	operation-cancelled(4),
	operation-started(5),
	...,
	operation-lost(6)
}
Messaging-Party-Information ::= SEQUENCE
{
	party-qualifier		[0] Messaging-Party-Qualifier,
	party-identity		[1] Messaging-Party-Identity,
	...,
	party-validity		[2] Messaging-Party-Validity OPTIONAL,
	copy-qualifier		[3]	Messaging-Copy-Qualifier OPTIONAL
}
Messaging-Party-Qualifier ::= ENUMERATED
{
	unknown-party(0),
		-- In this case the party cannot be classified as either originating or terminating
	originating-party(1),
		-- In this case, the partyInformation parameter provides the identities related to 
		-- the originating party and all information provided by this party.
	terminating-party(2),
		-- In this case, the partyInformation parameter provides the identities related to 
		-- the terminating party and all information provided by this party.
	...,
	associated-party(3)
		-- In this case, the partyInformation parameter provides the identites related to
		-- an associated party and all information provided by this party
}
Messaging-Party-Identity ::= CHOICE
{
	msisdn				[0] OCTET STRING (SIZE (1..9)),
		-- MSISDN of the target, encoded in the same format as the AddressString
		-- parameters defined in MAP format 3GPP TS 09.02 [22], clause 17.7.8.
	e164-format			[1] OCTET STRING (SIZE (1..25)),
		-- E.164 address of the node in international format. Coded in the same format as 
		-- the calling party number parameter of the ISUP (parameter part: EN 300 356 [23])
	email-address		[2] E-mail-Address-List,
	...,
	ip-address			[3] IPAddress,
		--IPAddress is defined by IETF RFC 791 [31] and RFC 2460 [34]
	alphanumeric		[4] UTF8String,
	ip-address-and-port [5] IP-Address-And-Port,
	imsi 				[6] OCTET STRING (SIZE (3..8)),
		-- International Mobile Subscriber Identity of the target, encoded in the same format as the
		-- TBCD-STRING parameter defined in MAP format 3GPP TS 29.002 [36], clause 17.7.8.
		-- It is described in 3GPP TS 23.003 [37] clause 2.2.
	imei 				[7] OCTET STRING (SIZE (8)),
		-- International Mobile Equipment Identity of the target, encoded in the same format as the
		-- TBCD-STRING parameter defined in MAP format 3GPP TS 23.003 [37] clause 6
	fax-url 			[8] OCTET STRING,
		-- see format defined in RFC 2806 [29].
	tel-url 			[9] OCTET STRING,
		-- see format used in TS 133.108 [5], TS 24 229[30] and defined in RFC 2806 [29].
	modem-url			[10] OCTET STRING,
		-- see format defined in RFC 2806 [29].
	sip-uri 			[11] OCTET STRING,
		-- see format used in in TS 133.108 [5] and defined in RFC 3261 [32].
	sips-uri 			[12] OCTET STRING,
		-- see format defined in RFC 3261 [32].
	nai 				[13] OCTET STRING 
		-- Network Access Identity of the party, encoded in the same format as used EPS 
		-- domain in TS 133.108 [5] and defined in RFC 4282 [33].
}
IP-Address-And-Port ::= SEQUENCE
{
	ip-address				[0] IPAddress,
		-- IPAddress is defined by IETF RFC 791 [31] and RFC 2460 [34]
	port-number				[1] INTEGER,
		-- port-number is defined by IETF RFC 6533 [35]
	...
}
Messaging-Party-Validity ::= ENUMERATED
{
	unknown(0),
	trusted(1),
	untrusted(2),
	...
}
Messaging-Copy-Qualifier ::= ENUMERATED
{
	unknown(0),
	none(1),
	cc(2),
	bcc(3),
	...
}
Messaging-Trigger ::= ENUMERATED
{
	unknown(0),
	user(1),
	user-agent(2),
	system(3),
	system-operator(4),
	...
}
Messaging-Property ::= CHOICE
{
	pincode				[0] OCTET STRING (SIZE (1..32)),
	...,
	priority			[1] Messaging-Property-Priority,
	greeting-type		[2] Messaging-Property-Greeting-Type,
	notification-type	[3] Messaging-Property-Notification-Type,
	language			[4] OCTET STRING,
		-- Language according to RFC 3066 [24]
	message-identifier	[5]	OCTET STRING,
	subject				[6]	UTF8String,
	user-agent			[7] UTF8String,
	password			[8] OCTET STRING,
	message-status		[9] Messaging-Property-Message-Status,
	requested-reports	[10] Messaging-Property-Requested-Reports,
	expires				[11] GeneralizedTime,
	message-date		[12] GeneralizedTime
}
Messaging-Property-Priority ::= ENUMERATED
{
	low(1),
	medium(2),
	high(3),
	private(4),
	...
}
Messaging-Property-Greeting-Type ::= ENUMERATED
{
	general(1),
	name(2),
	personal(3),
	absence(4),
	number(5),
	...
}
Messaging-Property-Notification-Type ::= ENUMERATED
{
	empty-call(1),
	lost-call(2),
	...,
	message-to-email(3),
	read-report(4),
	delivery-report(5),
	allow-delivery-report(6),
	deny-delivery-report(7),
	message-wait-indication(8),
--	voice-to-text(9),
	voice-to-text(254)					-- Carrier-specific temporary implementation (MH)
}
Messaging-Property-Message-Status ::= ENUMERATED
{
	indeterminate(0),
	expired(1),
	retrieved(2),
	rejected(3),
	deferred(4),
	forwarded(5),
	unrecognized(6),
	unreachable(7),
	read(8),
	deleted-without-being-read(9),
	delivery-condition-not-met(10),
	...
}
Messaging-Property-Requested-Reports ::= ENUMERATED
{
	none(0),
	delivery(1),
	read(2),
	delivery-and-read(3),
	...
}
END -- end of EmailPDU




-- Source: IPAccessPDU,ver10.txt
-- ETSI TS 102 232-3 V3.3.1 (2013-10)
-- Section 8 ASN.1 for IRI and CC
IPAccessPDU
{itu-t(0) identified-organization(4) etsi(0) securityDomain(2) lawfulIntercept(2) li-ps(5) iPAccess(3) version10(10)}

DEFINITIONS IMPLICIT TAGS ::=
BEGIN

IMPORTS
	-- from ETSI TS 101 671 [1]
	IPAddress
		FROM HI2Operations
		{itu-t(0) identified-organization(4) etsi(0) securityDomain(2) lawfulIntercept(2) hi2(1) version17(17)};

-- ============================
-- Object Identifier Definition
-- ============================

iPIRIObjId RELATIVE-OID				::= {li-ps(5) iPAccess(3) version10(10) iRI(1)}
iPCCObjId RELATIVE-OID				::= {li-ps(5) iPAccess(3) version10(10) cC(2)}
iPIRIOnlyObjId RELATIVE-OID			::= {li-ps(5) iPAccess(3) version10(10) iRIOnly(3)}
	-- all three definitions relative to {itu-t(0) identified-organization(4)
	-- etsi(0) securityDomain(2) lawfulintercept(2)}

-- ==========================
-- IP Communications Contents
-- ==========================

IPCC ::= SEQUENCE
{
	iPCCObjId			[0] RELATIVE-OID,
	iPCCContents		[1] IPCCContents
}

IPCCContents ::= CHOICE
{
	iPPackets			[0] OCTET STRING,
	...
}

-- ===================================================
-- Intercept-related information for general IP-Access
-- ===================================================

IPIRI ::= SEQUENCE
{
	iPIRIObjId			[0] RELATIVE-OID,
	iPIRIContents		[1] IPIRIContents,
	...
}

IPIRIContents ::= SEQUENCE
{
	accessEventType			[0] AccessEventType,
	targetUsername			[1] OCTET STRING,
		-- in ASCII characters
	internetAccessType		[2] InternetAccessType,
	iPVersion				[3] IPVersion,
	targetIPAddress			[4] IPAddress OPTIONAL,
		-- IP address may not be available in case of failed logon attempts.
		-- If it is available, it must be sent.
		-- This field will carry the first IPv4 or IPv6 target IP address with or without 
		-- subnet. Use of this field is fully described in section 6.2.1.
	targetNetworkID			[5] UTF8String (SIZE (1..20)) OPTIONAL,
		-- Target network ID (e.g. MAC address, PSTN number)
	targetCPEID				[6] UTF8String (SIZE (1..128)) OPTIONAL,
		-- CPEID (e.g. Relay Agent info, computer name)
	targetLocation			[7] UTF8String (SIZE (1..64)) OPTIONAL,
		-- When internetAccessType is Wireless LAN, this field should contain a string which
		-- uniquely identifies the wireless accesspoint within the SvP domain
	pOPPortNumber			[8] INTEGER (0..4294967295) OPTIONAL,
		-- The POP port number used by the target
	callBackNumber			[9] UTF8String (SIZE (1..20)) OPTIONAL,
		-- The number used to call-back the target
	startTime				[10] GeneralizedTime OPTIONAL,
		-- The start date-time of the session or lease
	endTime					[11] GeneralizedTime OPTIONAL,
		-- The actual end date-time of the session or lease
	endReason				[12] EndReason OPTIONAL,
		-- The reason for the session to end
	octetsReceived			[13] INTEGER (0..18446744073709551615) OPTIONAL,
		-- The number of octets the target received
	octetsTransmitted		[14] INTEGER (0..18446744073709551615) OPTIONAL,
		-- The number of octets the target transmitted
	rawAAAData			 [15] OCTET STRING OPTIONAL,
		-- Content of the raw AAA record
	...,
	expectedEndTime			[16] GeneralizedTime OPTIONAL,
		-- The expected end date-time of the session or lease
	pOPPhoneNumber			[17] UTF8String (SIZE (1..20)) OPTIONAL,
		-- The phone number dialed by the target for dial-up
	pOPIdentifier			[18] IPIRIIDType OPTIONAL,
		-- The identifier or name of the POP
	pOPIPAddress			[19] IPAddress OPTIONAL,
		-- The IP address of the POP
	nationalIPIRIParameters	[20] NationalIPIRIParameters OPTIONAL,
		-- National IP IRI Parameters
	additionalIPAddress		[21] IPAddress OPTIONAL,
		-- This field will carry the first IPv6 target IP address with or without prefix when the 
		-- iPVersion parameter is set to iPV4andV6.
		-- Use of this field is fully described in section 6.2.1
	authenticationType		[22] AuthenticationType OPTIONAL,
		-- Field used to identify the authentication type to assist with LEMF data validation
	otherTargetIdentifiers	[23] SEQUENCE OF OtherTargetIdentifiers OPTIONAL
		-- This parameter will carry the second and subsequent IPv4 or IPv6 target IP addresses
		-- It is used when multiple subnet/prefix ranges are assigned to a target service.
		-- Use of this field is fully described in section 6.2.1
}

AccessEventType ::= ENUMERATED
{
	accessAttempt(0),
		-- A target requests access to the IAS
	accessAccept(1),
		-- IAS access is granted to the target, the session begins
	accessReject(2),
		-- IAS access is refused to the target
	accessFailed(3),
		-- The Access_attempt timed-out or failed otherwise
	sessionStart(4),
		-- A target starts using the IAS; not in use anymore from version 4(4)
	sessionEnd(5),
		-- A target stops using the IAS; not in use anymore from version 4(4)
	interimUpdate(6),
		-- Intermediate status report on service status or usage
	...,
	startOfInterceptionWithSessionActive(7),
		-- LI is started on a target who already has an active session
	accessEnd(8),
		-- A target stops using the IAS, the session ends
	endOfInterceptionWithSessionActive(9),
	 	-- LI is ended on a target who still has an active session
	unknown(10)
}

InternetAccessType ::= ENUMERATED
{
	undefined(0),
	dialUp(1),
		-- IAS via DialUp access
	xDSL(2),
		-- IAS via DSL access
	cableModem(3),
		-- IAS via Cable access
	lAN(4),
		-- IAS via LAN access
	...,
	wirelessLAN(5),
		-- IAS via Wireless LAN access
	fTTx(6),
		-- IAS via Fiber access
	wIMAX-HIPERMAN(7),
		-- IAS via WIMAX/HIPERMAN (fixed access)
	satellite(8),
		-- IAS via Satellite access
		-- (when it is not covered by any 3GPP or ETSI mobile Lawful Interception specifications)
	wireless-other(9)
		-- IAS via other type of Wireless access
		-- (when it is not covered by any 3GPP or ETSI mobile Lawful Interception specifications)
}

IPVersion ::= ENUMERATED
{
	iPV4(1),
		-- The IPv4 protocol is used
	iPV6(2),
		-- The IPv6 protocol is used
	iPV4andV6(3),
		-- The IPv4 and IPv6 protocols are used
	...
}

EndReason ::= ENUMERATED
{
	undefined(0),
	regularLogoff(1),
		-- The target logged off
	connectionLoss(2),
		-- The connection was lost
	connectionTimeout(3),
		-- The connection timed-out
	leaseExpired(4),
		-- The DHCP lease expired
	...
}

IPIRIIDType ::= CHOICE
{
	printableIDType			[0] UTF8String (SIZE (1..128)),
		-- For printable userIDs, such as the Radius username, phonenumbers
	macAddressType			[1] OCTET STRING (SIZE (6)),
		-- For MAC address types, raw binary format as in RFC 2132 [15]
	ipAddressType			[2] IPAddress,
		-- For IP address types
	...
}

NationalIPIRIParameters ::= SEQUENCE
{
	countryCode		[1] PrintableString (SIZE (2)),
		-- Country Code according to ISO 3166-1 [16],
		-- the country to which the parameters inserted after the extension marker apply.
	...
	-- In case a given country wants to use additional national parameters according to its law,
	-- these national parameters should be defined using the ASN.1 syntax and added after the
	-- extension marker (...).
	-- It is recommended that "version parameter" and "vendor identification parameter" are
	-- included in the national parameters definition. Vendor identifications can be
	-- retrieved from the IANA web site (see Annex E Bibliography). Besides, it is recommended 
	-- to avoid using tags from 240 to 255 in a formal type definition.
}

AuthenticationType ::= ENUMERATED
{
	unknown(0),
		-- AAA function for the target service is unknown
	static(1),
		-- The target service is assigned a static IP address & no AAA expected
	radiusAAA(2),
		-- AAA function for the target service is provided by RADIUS
	dhcpAAA(3),
		-- AAA function for the target service is provided by DHCP
	diameterAAA(4),
		-- AAA function for the target service is provided by DIAMETER
	...
}

OtherTargetIdentifiers ::= CHOICE
{
		-- Additional target identifiers associated with the target service
		-- This list is extensible to accommodate other target identifiers which 
		-- may be required in future.
	iPAddress		[0] IPAddress,
		-- IPAddress imported from TS 101 671 [1].
		-- This can be an IPv4 address (with or without a subnet range defined) or 
		-- an IPv6 address (with or without a prefix range defined).
	...
}

-- =====================================================
-- Intercept-related information for IRI-Only intercepts
-- =====================================================

IPIRIOnly ::= SEQUENCE
{
	iPIRIOnlyObjId				[0] RELATIVE-OID,
	iPInformation				[1] IPInformation,
	protocolInformation			[2] ProtocolInformation,
	iPAggregatedNbrOfPackets	[3] INTEGER OPTIONAL,
	iPAggregatedNbrOfBytes		[4] INTEGER OPTIONAL,
	...
}

IPInformation ::= CHOICE
{
	iPv4Information		[0] IPv4Information,
	iPv6Information		[1] IPv6Information
}

ProtocolInformation ::= CHOICE
{
	none					[0] NULL,
		-- No layer 4 protocol information is provided
	tCPInformation			[1] TCPInformation,
	uDPInformation			[2] UDPInformation,
	...
}

IPv4Information ::= SEQUENCE
{
	headerLength			[0] OCTET STRING OPTIONAL,
	typeOfService			[1] OCTET STRING OPTIONAL,
	totalLength				[2] OCTET STRING (SIZE (2))OPTIONAL,
	identification			[3] OCTET STRING (SIZE (2))OPTIONAL,
	fragment				[4] OCTET STRING (SIZE (2))OPTIONAL,
	ttl						[5] OCTET STRING OPTIONAL,
	protocol				[6] OCTET STRING OPTIONAL,
	headerChecksum			[7] OCTET STRING (SIZE (2))OPTIONAL,
	source					[8] OCTET STRING (SIZE (4)),
	destination				[9] OCTET STRING (SIZE (4)),
	options					[10] OCTET STRING (SIZE (0..40))OPTIONAL
}

IPv6Information ::= SEQUENCE
{
	trafficClass			[0] OCTET STRING OPTIONAL,
	flowLabel				[1] OCTET STRING (SIZE (20))OPTIONAL,
	payloadLength			[2] OCTET STRING (SIZE (4))OPTIONAL,
	nextHeader				[3] OCTET STRING OPTIONAL,
	hopLimit				[4] OCTET STRING OPTIONAL,
	source					[5] OCTET STRING (SIZE (16)),
	destination				[6] OCTET STRING (SIZE (16))
}

TCPInformation ::= SEQUENCE
{
	sourcePort			[0] OCTET STRING (SIZE (2))OPTIONAL,
	destinationPort		[1] OCTET STRING (SIZE (2))OPTIONAL,
	sequenceNumber		[2] OCTET STRING (SIZE (4))OPTIONAL,
	ackNumber			[3] OCTET STRING (SIZE (4))OPTIONAL,
	dataOffset			[4] BIT STRING (SIZE (4))OPTIONAL,
		-- First 4 bits
	controlBits			[5] BIT STRING (SIZE (6))OPTIONAL,
		-- Last 6 bits
	windowSize			[6] OCTET STRING (SIZE (2))OPTIONAL,
	checkSum			[7] OCTET STRING (SIZE (2))OPTIONAL,
	urgentPointer		[8] OCTET STRING (SIZE (2))OPTIONAL,
	options				[9] OCTET STRING (SIZE (0..40))OPTIONAL
}

UDPInformation ::= SEQUENCE
{
	sourcePort			[0] OCTET STRING (SIZE (2))OPTIONAL,
	destinationPort		[1] OCTET STRING (SIZE (2))OPTIONAL,
	length				[2] OCTET STRING (SIZE (2))OPTIONAL,
	checkSum			[3] OCTET STRING (SIZE (2))OPTIONAL
}

END -- end of IPAccessPDU




-- Source:L2AccessPDU,ver7.txt
-- ETSI TS 102 232-4 V3.2.2 (2014-07)
-- Section 8.1 ASN.1 specification
L2AccessPDU 
{itu-t(0) identified-organization(4) etsi(0) securityDomain(2) lawfulIntercept(2)
li-ps(5) l2Access(4) version7(7)}

DEFINITIONS IMPLICIT TAGS ::=
BEGIN

-- ============================
-- Object Identifier Definition
-- ============================

l2IRIObjId RELATIVE-OID			::= {li-ps(5) l2Access(4) version7(7) iRI(1)}
l2CCObjId RELATIVE-OID			::= {li-ps(5) l2Access(4) version7(7) cC(2)}
l2IRIOnlyObjId RELATIVE-OID		::= {li-ps(5) l2Access(4) version7(7) iRIOnly(3)}
	-- all three definitions relative to {itu-t(0) identified-organization(4)
	-- etsi(0) securityDomain(2) lawfulintercept(2)}

-- ==========================
-- L2 Communications Contents
-- ==========================

L2CC		::= SEQUENCE
{
	l2CCObjId 				[0] RELATIVE-OID,
	l2CCContents			[1] CHOICE
	{
		l2TP			[1] OCTET STRING,
			-- The L2TP protocol is used
		l2F				[2] OCTET STRING,
			-- The L2F protocol is used
		pPTP			[3] OCTET STRING,
			-- The PPTP protocol is used
		pPP				[4] OCTET STRING,
			-- The PPP protocol is used
		ethernet		[5] OCTET STRING,
			-- The ethernet protocol is used
		...,
		l2ATM2684		[6] OCTET STRING,
			-- The protocol RFC 2684, method "LLC Encapsulation for Bridged Protocols` [16] is used
		l2FR2427		[7] OCTET STRING
			-- The protocol RFC 2427 “Multiprotocol Interconnect over Frame Relay” [18] is used
	}
}

-- ===================================================
-- Intercept-related information for general L2-Access
-- ===================================================

L2IRI			::= SEQUENCE
{
	l2IRIObjId 			[0] RELATIVE-OID,
	l2IRIContents		[1] L2IRIContents,
	...
}

L2IRIContents			::= SEQUENCE
{
	accessEventType				[0] AccessEventType,
	internetAccessType			[2] InternetAccessType OPTIONAL,
	targetNetworkID				[5] UTF8String (SIZE (1..128)) OPTIONAL,
		-- Target network ID (e.g. MAC address, PSTN number, additional information from
		-- network elements)
	targetCPEID					[6] UTF8String (SIZE (1..128)) OPTIONAL,
		-- CPEID (e.g. Relay Agent info, computer name)
	targetLocation				[7] UTF8String (SIZE (1..64))OPTIONAL,
		-- <for further study>
	nASPortNumber				[8] INTEGER (0..4294967295) OPTIONAL,
		-- The NAS port number used by the target
	callBackNumber				[9] UTF8String (SIZE (1..20)) OPTIONAL,
		-- The number used to call-back the target
	startTime					[10] GeneralizedTime OPTIONAL,
		-- The start date-time of the session or lease
	endTime						[11] GeneralizedTime OPTIONAL,
			-- The end date-time of the session or lease
	endReason					[12] EndReason OPTIONAL,
		-- The reason for the session to end
	octetsReceived				[13]	INTEGER (0..18446744073709551615) OPTIONAL,
		-- The number of octets the target received
	octetsTransmitted			[14]	INTEGER (0..18446744073709551615) OPTIONAL,
		-- The number of octets the target transmitted
	rawAAAData					[15]	OCTET STRING OPTIONAL,
		-- Content of the raw AAA record
	...,
	authenticationType			[16] AuthenticationType OPTIONAL
		-- Field used to identify the authentication type to assist with LEMF data validation
}

AccessEventType			::= ENUMERATED
{
	accessAttempt(0),
		-- A target requests access to the IAS
	accessAccept(1),
		 -- IAS access is granted to the target, the session begins
	accessReject(2),
		-- IAS access is refused to the target
	accessFailed(3),
		-- The Access_attempt timed-out or failed otherwise
	sessionStart(4),
		-- A target starts using the IAS; not in use anymore from version 4(4).
	sessionEnd(5),
		-- A target stops using the IAS; not in use anymore from version 4(4).
	interimUpdate(6),
		-- Intermediate status report on service status or usage
	unknown(7),
	...,
	startOfInterceptionWithSessionActive(8),
		-- LI is started on a target who already has an active session
	accessEnd(9),
		-- A target stops using the IAS, the session ends.
	endOfInterceptionWithSessionActive(10)
		-- LI is ended on a target who still has an active session
}

InternetAccessType		::= ENUMERATED
{
	undefined(0),
	dialUp(1),
		-- IAS via DialUp access
	xDSL(2),
		-- IAS via DSL access
	cableModem(3),
		-- IAS via Cable access
	lAN(4),
		-- IAS via LAN access
	...,
	wirelessLAN(5),
		-- IAS via Wireless LAN access
	fTTx(6),
		-- IAS via Fiber access
	wIMAX-HIPERMAN(7),
		-- IAS via WIMAX/HIPERMAN (fixed access)
	satellite(8)
		-- IAS via Satellite access
		-- (when it is not covered by any 3GPP or ETSI mobile Lawful Interception specifications)
}

EndReason			::= ENUMERATED
{
	undefined(0),
	regularLogoff(1),
		-- The target logged off
	connectionLoss(2),
		-- The connection was lost
	connectionTimeout(3),
		-- The connection timed-out
	leaseExpired(4),
		-- The DHCP lease expired
	...
}

AuthenticationType ::= ENUMERATED
{
	unknown(0),
		-- AAA function for the target service is unknown
	static(1),
		-- The target service is assigned a static IP address & no AAA expected
	radiusAAA(2),
		-- AAA function for the target service is provided by RADIUS
	dhcpAAA(3),
		-- AAA function for the target service is provided by DHCP
	diameterAAA(4),
		-- AAA function for the target service is provided by DIAMETER
	...
}


-- =====================================================
-- Intercept-related information for IRI-Only intercepts
-- =====================================================

L2IRIOnly		::= SEQUENCE
{
	l2IRIOnlyObjId					[0] RELATIVE-OID,
	l2protocolInformation		[2] L2ProtocolInformation,
	l2AggregatedNbrOfPackets	[3] INTEGER OPTIONAL,
	l2AggregatedNbrOfBytes		[4] INTEGER OPTIONAL,
	...
}

L2ProtocolInformation		::= ENUMERATED
{
	l2ProtocolL2tp(1),
		-- The L2TP protocol is used
	l2ProtocolL2f(2),
		-- The L2F protocol is used
	l2ProtocolPptp(3),
		-- The PPTP protocol is used
	l2ProtocolPpp(4),
		-- The PPP protocol is used
	ethernetProtocol(5),
		-- The ethernet protocol is used
	undefined(6),
	...,
	l2ProtocolATM2684(7),
		-- The protocol RFC 2684, method "LLC Encapsulation for Bridged Protocols" [16] is used
	l2ProtocolFR2427(8)
		-- The protocol RFC2427 “Multiprotocol Interconnect over Frame Relay” [18] is used
}

END -- end of L2AccessPDU




-- Source: IPMultimediaPDU,ver7.txt
-- ETSI TS 102 232-5 V3.5.1 (2015-10)
-- Section 7 ASN.1 specification for IRI and CC
IPMultimediaPDU 

{itu-t(0) identified-organization(4) etsi(0) securityDomain(2) lawfulIntercept(2) li-ps(5) iPMultimedia(5) version7(7)}



DEFINITIONS IMPLICIT TAGS ::=

BEGIN



IMPORTS

	-- from TS 101 671 [1]

	IPAddress

		FROM HI2Operations 

		{itu-t(0) identified-organization(4) etsi(0) securityDomain(2) lawfulIntercept(2) hi2(1) version16(16)}

		

	-- from TS 102 232-1 [2]

	Location

		FROM LI-PS-PDU

		{itu-u(0) identified-organization(4) etsi(0) securityDomain(2) lawfulIntercept(2) li-ps(5) genHeader(1) version19(19)};







-- ============================

-- Object Identifier Definition

-- ============================



iPMMIRIObjId RELATIVE-OID			::= {li-ps(5) iPMultimedia(5) version7(7) iRI(1)}

iPMMCCObjId RELATIVE-OID			::= {li-ps(5) iPMultimedia(5) version7(7) cC(2)}

	-- both definitions relative to: 

	-- {itu-t(0) identified-organization(4) etsi(0) securityDomain(2) lawfulIntercept(2)}



-- =====================================

-- IP Multimedia Communications Contents

-- =====================================



IPMMCC ::= SEQUENCE

{

	iPMMCCObjId					[0] RELATIVE-OID,

	mMCCContents				[1] OCTET STRING,

		-- Copy of the multimediastream, i.e. all related RTP/RTCP, UDPTL or MSRP packets

		-- Each IPMMCC shall contain one intercepted packet

		-- Protocol of the multimedia packets is indicated by means of mMCCprotocol parameter

		-- mMCCContents was called rTPCCContents in earlier versions until v2.3.2.

	...,

	frameType					[2] FrameType OPTIONAL,

		-- The availability of header information shall be signalled with the frameType parameter

		-- The module is defined as OPTIONAL because of backwards compatibility reasons

		-- For new implementations the module is MANDATORY to be used as defined in clause 5.5

	streamIdentifier			[3] OCTET STRING OPTIONAL,

		-- Used to identify the media stream within the current CIN, typically in case of 

		-- multiple media streams communications

		-- May be used to correlate each media stream with the relevant SDP media description of IRI

		-- May contain c= and m= lines extracts for instance

	mMCCprotocol				[4] MMCCprotocol OPTIONAL

		-- Used to identify the protocol of packets sent in MMCCContent (RTP, UDPTL, MSRP, etc.)

		-- Absence means mMCCContents contains RTP/RTCP packets

}



FrameType ::= ENUMERATED

{

	ipFrame(0),

		-- All headers are present

	udpFrame(1),

		-- IP header is missing

	rtpFrame(2),

		-- UDP and IP headers are missing

	audioFrame(3),

		-- All headers are missing

	...,

	tcpFrame(4),

		-- IP header is missing

	artificialRtpFrame(5),

		-- UDP and IP headers are missing, artificial RTP frame has been added

	udptlFrame(6)

		-- UDP and IP headers are missing

}



MMCCprotocol ::= ENUMERATED

{

	rTP(0),

		-- mMCCContents parameter contains RTP/RTCP packets

	mSRP(1),

		-- mMCCContents parameter contains MSRP packets

	...,

	uDPTL(2)

		-- mMCCContents parameter contains UDPTL packets

}



-- ========================================================

-- Intercept-related information for IP Multimedia sessions

-- ========================================================



IPMMIRI ::= SEQUENCE

{

	iPMMIRIObjId				[0] RELATIVE-OID,

	iPMMIRIContents				[1] IPIRIContents,

	...,

	targetLocation				[2] Location OPTIONAL

		-- This common parameter is defined in TS 102 232-1 [2], the use of this parameter is described in clause 5.2.3



}



IPIRIContents ::= CHOICE

{

	originalIPMMMessage			[0] OCTET STRING,

		-- Copy of the IP MM signalling packet including the original IP and UDP/TCP headers

	sIPMessage					[1] SIPMessage,

		-- Copy of the SIP content and the source and destination IP address

	h323Message					[2] H323Message,

		-- Copy of the H.323 content and the source and destination IP address

	...,

	nationalIPMMIRIParameters	[3] NationalIPMMIRIParameters

		-- This parameter is used according to national regulations

		-- This parameter shall be delivered as an IRI-Report-record

}



SIPMessage ::= SEQUENCE

{

	iPSourceAddress				[0] IPAddress,

	iPDestinationAddress		[1] IPAddress,

	sIPContent					[2] OCTET STRING,

	...

}



H323Message ::= SEQUENCE

{

	iPSourceAddress				[0] IPAddress,

	iPDestinationAddress		[1] IPAddress,

	h323Content					[2] H323MessageContent,

	...

}



H323MessageContent ::= CHOICE

{

	h225CSMessageContent		[0] OCTET STRING,

	h225RASMessageContent		[1] OCTET STRING,

	h245MessageContent			[2] OCTET STRING,

	genericMessageContent		[3] OCTET STRING,

	...

}



NationalIPMMIRIParameters ::= SEQUENCE

{

	countryCode					[1] PrintableString (SIZE (2)),

		-- Country Code according to ISO 3166-1 [16],

		-- the country to which the parameters inserted after the extension marker apply.

	...

	-- In case a given country wants to use additional national parameters according to its law,

	-- these national parameters should be defined using the ASN.1 syntax and added after the

	-- extension marker (...).

	-- It is recommended that "version parameter" and "vendor identification parameter" are

	-- included in the national parameters definition. Vendor identifications can be

	-- retrieved from the IANA web site (see Annex E Bibliography). Besides, it is recommended 

	-- to avoid using tags from 240 to 255 in a formal type definition.

}



END -- end of IP Multimedia PDU






-- Source: PstnIsdnPDU,ver5.txt
-- ETSI TS 102 232-6 V3.3.1 (2014-03)
-- Annex A.2 ASN.1 definitions

PstnIsdnPDU
{itu-t(0) identified-organization(4) etsi(0) securityDomain(2) lawfulIntercept(2) li-ps(5) pstnIsdn(6) version5(5)}

DEFINITIONS IMPLICIT TAGS ::=
BEGIN

IMPORTS

	

	-- from TS 102 232-01 [2]
	PayloadDirection
		FROM LI-PS-PDU
		{itu-t(0) identified-organization(4) etsi(0) securityDomain(2) lawfulIntercept(2) li-ps(5) genHeader(1) version18(18)};


-- ============================
-- Object Identifier Definition
-- ============================

	-- definitions are relative to
	-- {itu-t(0) identified-organization(4) etsi(0) securityDomain(2) lawfulintercept(2)}
pstnIsdnIRIObjId RELATIVE-OID	::= {li-ps(5) pstnIsdn(6) version5(5) iRI(1)}
pstnIsdnCCObjId RELATIVE-OID	::= {li-ps(5) pstnIsdn(6) version5(5) cC(2)}


-- ===============================
-- Description of the PstnIsdn IRI
-- ===============================

PstnIsdnIRI ::= SEQUENCE
{
	pstnIsdnIRIObjId		[0] RELATIVE-OID,
	pstnIsdnIRIContents		[1] PstnIsdnIRIContents
}

PstnIsdnIRIContents ::= CHOICE
{
	supplementaryInfo		[0] SupplementaryInfo,
	...
}

SupplementaryInfo ::= SEQUENCE
{
	informationAppliesTo	[0] InformationAppliesTo,
		-- Identifies the PDUs to which this info applies
	mediaFormat				[1] INTEGER (0..127),
		-- As defined in RFC 3551 [10]
	mediaAttributes			[2] OCTET STRING OPTIONAL,
		-- Format as per RFC 4566 [7]
		-- Clause 6.3 describes when the mediaAttributes shall be present
	encryptionKey			[3] OCTET STRING OPTIONAL,
		-- Format as per RFC 4566 [7]
	sessionName				[4] OCTET STRING OPTIONAL,
		-- Format as per RFC 4566 [7]
	sessionInfo				[5] OCTET STRING OPTIONAL,
		-- Format as per RFC 4566 [7]
	copyOfSDPMessage		[6] OCTET STRING OPTIONAL,
		-- Format as per RFC 4566 [7]
	...,
	frameType				[7] FrameType OPTIONAL,
		-- Populated if one or more protocol layers are missing from CC data
		-- May be omitted if all headers are present.
	alternateProtocol		[8] AlternateProtocol OPTIONAL
		-- Used to identify the protocol of packets sent in pstnIsdnCCContents


}

InformationAppliesTo ::= SEQUENCE
	-- Identifies the PDUs to which a piece of supplementary information applies
{
	payloadDirection		[0] PayloadDirection,
		-- The direction of the traffic to which this info applies
	cCLinkID				[1] INTEGER (0..65535) OPTIONAL,
		-- If there are multiple CCLinks, this field states CCLink to which this info applies
	firstPDUNumber			[2] INTEGER (0..4294967295) OPTIONAL,
		-- The supplementary info applies to all PDUs with this sequence number and above
	...
}

FrameType ::= ENUMERATED
{
	ipFrame(0),
		-- All headers are present. Use AlternateProtocol to signal the contents if not RTP
	udpFrame(1),
		-- IP header is missing. Use AlternateProtocol to signal the contents if not RTP
	applicationFrame(2),
		-- UDP and IP headers are missing. Use AlternateProtocol to signal the contents if not RTP
	audioFrame(3),
		-- All headers are missing
	...,
	artificialRtpFrame(4)
		-- UDP and IP headers are missing, artificial RTP frame has been added

}
AlternateProtocol ::= ENUMERATED
{
	uDPTL(1),
		-- pstnIsdnCCContents parameter contains UDPTL packets
	...
}


-- ==============================
-- Description of the PstnIsdn CC
-- ==============================

PstnIsdnCC ::= SEQUENCE
{
	pstnIsdnCCObjId			[0] RELATIVE-OID,
	pstnIsdnCCContents		[1] OCTET STRING,
		-- See clause 6.2 for definition of format of PstnIsdn CC
	cCLinkID				[2] INTEGER (0..65535) OPTIONAL,
		-- Shall be present if multiple CCLinks are used (see clause 6.3.4)
	...,
	supplementaryInfo		[3] SupplementaryInfo OPTIONAL
		-- Shall be present at least in the first PDU
}

END -- end of PstnIsdnPDU




-- Source: UmtsHI2Operations,rel12.txt 
-- ETSI TS 133 108 V12.11.0 (2016-01)
-- B.3	Intercept related information (HI2 PS and IMS)
UmtsHI2Operations {itu-t(0) identified-organization(4) etsi(0) securityDomain(2) lawfulintercept(2) threeGPP(4) hi2(1) r12(12) version-9 (9)} 

DEFINITIONS IMPLICIT TAGS ::=

BEGIN

IMPORTS 

		OPERATION, 
		ERROR 
			FROM Remote-Operations-Information-Objects 
			{joint-iso-itu-t(2) remote-operations(4) informationObjects(5) version1(0)}

		LawfulInterceptionIdentifier,
		TimeStamp,
		Network-Identifier,
		National-Parameters,
		National-HI2-ASN1parameters,
		DataNodeAddress,
		IPAddress,
		IP-value,
		X25Address

			FROM HI2Operations
			{itu-t(0) identified-organization(4) etsi(0) securityDomain(2)
 				  lawfulIntercept(2) hi2(1) version18(18)}; -- Imported from TS 101 671v3.12.1
			

-- Object Identifier Definitions

-- Security DomainId
lawfulInterceptDomainId OBJECT IDENTIFIER ::= {itu-t(0) identified-organization(4) etsi(0)
securityDomain(2) lawfulIntercept(2)}

-- Security Subdomains
threeGPPSUBDomainId OBJECT IDENTIFIER ::= {lawfulInterceptDomainId threeGPP(4)}
hi2DomainId OBJECT IDENTIFIER	::= {threeGPPSUBDomainId hi2(1) r12(12) version-8 (8)}

umts-sending-of-IRI  OPERATION ::= 
{
	ARGUMENT	UmtsIRIsContent
	ERRORS		{ OperationErrors }
	CODE		global:{threeGPPSUBDomainId hi2(1) opcode(1)}
}
-- Class 2 operation . The timer shall be set to a value between 3 s and 240 s. 
-- The timer.default value is 60s.
-- NOTE:	The same note as for HI management operation applies.

UmtsIRIsContent		::= CHOICE
{
	umtsiRIContent			UmtsIRIContent,
	umtsIRISequence			UmtsIRISequence
}

UmtsIRISequence		::= SEQUENCE OF UmtsIRIContent

-- Aggregation of UmtsIRIContent is an optional feature.
-- It may be applied in cases when at a given point in time
-- several IRI records are available for delivery to the same LEA destination.
-- As a general rule, records created at any event shall be sent
-- immediately and not withheld in the DF or MF in order to
-- apply aggragation.
-- When aggregation is not to be applied,  
-- UmtsIRIContent needs to be chosen.


UmtsIRIContent		::= CHOICE 
{
	iRI-Begin-record		[1] IRI-Parameters,	-- include at least one optional parameter 
	iRI-End-record			[2] IRI-Parameters,
	iRI-Continue-record		[3] IRI-Parameters,	-- include at least one optional parameter 
	iRI-Report-record		[4] IRI-Parameters	-- include at least one optional parameter 
}

unknown-version 		ERROR ::= { CODE local:0}
missing-parameter		ERROR ::= { CODE local:1}
unknown-parameter-value	ERROR ::= { CODE local:2}
unknown-parameter		ERROR ::= { CODE local:3}

OperationErrors ERROR ::= 
{ 
	unknown-version | 
	missing-parameter | 
	unknown-parameter-value | 
	unknown-parameter 
}
-- This values may be sent by the LEMF, when an operation or a parameter is misunderstood.

-- Parameters having the same tag numbers must be identical in Rel-5 and onwards modules.
IRI-Parameters		::= SEQUENCE 
{
	hi2DomainId				[0]	OBJECT IDENTIFIER,  -- 3GPP HI2 domain
	iRIversion				[23] ENUMERATED
	{
		version2 (2),
		...,
		version3 (3),
		version4 (4),
			-- note that version5 (5) cannot be used as it was missed in the version 5 of this
			-- ASN.1 module.
		version6 (6),
			-- vesion7(7) was ommited to align with ETSI TS 101 671.
		lastVersion (8)	} OPTIONAL,
		-- Optional parameter "iRIversion" (tag 23) was always redundant in 33.108, because 
		-- the object identifier "hi2DomainId" was introduced into "IRI Parameters" in the 
		-- initial version of 33.108v5.0.0. In order to keep backward compatibility, even when
		-- the version of the "hi2DomainId" parameter will be incremented it is recommended
		-- to always send to LEMF the same: enumeration value "lastVersion(8)".
		-- if not present, it means version 1 is handled
	lawfulInterceptionIdentifier	[1] LawfulInterceptionIdentifier,
		-- This identifier is associated to the target.
	timeStamp				[3] TimeStamp, 
		-- date and time of the event triggering the report.) 
	initiator 				[4] ENUMERATED 
	{
		not-Available		(0),
		originating-Target	(1),
			-- in case of GPRS, this indicates that the PDP context activation, modification 
			-- or deactivation is MS requested
		terminating-Target	(2),
			-- in case of GPRS, this indicates that the PDP context activation, modification or
			-- deactivation is network initiated
	...
	} OPTIONAL,

	locationOfTheTarget		[8] Location OPTIONAL,
		-- location of the target 
	partyInformation 		[9] SET SIZE (1..10) OF PartyInformation OPTIONAL, 
		-- This parameter provides the concerned party, the identiy(ies) of the party
		--)and all the information provided by the party. 

	serviceCenterAddress	[13] PartyInformation OPTIONAL,
		-- e.g. in case of SMS message this parameter provides the address of  the relevant 
		-- server within the calling (if server is originating) or called (if server is
		-- terminating) party address parameters
	sMS						[14] SMS-report OPTIONAL,
		-- this parameter provides the SMS content and associated information

	national-Parameters		[16] National-Parameters OPTIONAL,
	gPRSCorrelationNumber	[18] GPRSCorrelationNumber OPTIONAL,
	gPRSevent 				[20] GPRSEvent OPTIONAL,
		-- This information is used to provide particular action of the target
		-- such as attach/detach
	sgsnAddress 			[21] DataNodeAddress OPTIONAL,
	gPRSOperationErrorCode 	[22] GPRSOperationErrorCode OPTIONAL,
	ggsnAddress 			[24] DataNodeAddress OPTIONAL,
	qOS						[25] UmtsQos OPTIONAL,
	networkIdentifier		[26] Network-Identifier OPTIONAL,
	sMSOriginatingAddress 	[27] DataNodeAddress OPTIONAL,
	sMSTerminatingAddress 	[28] DataNodeAddress OPTIONAL,
	iMSevent				[29] IMSevent OPTIONAL,
	sIPMessage				[30] OCTET STRING  OPTIONAL,
	servingSGSN-number		[31] OCTET STRING (SIZE (1..20))	OPTIONAL, 
                               -- Coded according to 3GPP TS 29.002 [4] and 3GPP TS 23.003 25].
	servingSGSN-address		[32] OCTET STRING (SIZE (5..17)) 	OPTIONAL,
								-- Octets are coded according to 3GPP TS 23.003 [25]
	..., 
 			-- Tag			[33] was taken into use by ETSI module in TS 101 671v2.13.1
	ldiEvent	 			[34] LDIevent OPTIONAL,
	correlation 			[35] CorrelationValues OPTIONAL,
	mediaDecryption-info	[36] MediaDecryption-info OPTIONAL, 
	servingS4-SGSN-address	[37] OCTET STRING OPTIONAL,
	-- Diameter Origin-Host and Origin-Realm of the S4-SGSN based on the TS 29.272 [59]. 
	-- Only the data fields from the Diameter AVPs are provided concatenated 
	-- with a semicolon to populate this field. 
    sipMessageHeaderOffer   [38] OCTET STRING OPTIONAL,
    sipMessageHeaderAnswer  [39] OCTET STRING OPTIONAL,
    sdpOffer                [40] OCTET STRING OPTIONAL,
    sdpAnswer               [41] OCTET STRING OPTIONAL, 
    uLITimestamp            [42] OCTET STRING (SIZE (8)) OPTIONAL,
    -- Coded according to 3GPP TS 29.060 [17]; Only the ULI Timestamp value is reported. 
	packetDataHeaderInformation		 [43] PacketDataHeaderInformation	OPTIONAL, 
	mediaSecFailureIndication       [44] MediaSecFailureIndication OPTIONAL,    
	pANI-Header-Info		[45] SEQUENCE OF PANI-Header-Info		OPTIONAL,
    -- information extracted from P-Access-Network-Info headers of SIP message; 
	-- described in TS 24.229 §7.2A.4 [76] 
    imsVoIP					[46] IMS-VoIP-Correlation	OPTIONAL,
	xCAPmessage				[47] OCTET STRING OPTIONAL,	
	-- The entire HTTP contents of any of the target"s IMS supplementary service setting 
	-- management or manipulation XCAP messages, mainly made through the Ut 
	-- interface defined in the 3GPP TS 24 623 [77].


	national-HI2-ASN1parameters	[255]	National-HI2-ASN1parameters	OPTIONAL
}
-- Parameters having the same tag numbers must be identical in Rel-5 and onwards modules

-- PARAMETERS FORMATS

PANI-Header-Info::= SEQUENCE
{
    access-Type 		[1] OCTET STRING 		OPTIONAL,
    -- ASCII chain "3GPP-GERAN",... : see TS 24.229 §7.2A.4 [76] 
    access-Class  		[2] OCTET STRING		OPTIONAL,
    -- ASCII chain"3GPP-GERAN",... : see TS 24.229 §7.2A.4 [76]
    network-Provided	[3] NULL				OPTIONAL,
    -- present if provided by the network
    pANI-Location		[4] PANI-Location 		OPTIONAL,
    ...
}

PANI-Location  ::= SEQUENCE
{
    raw-Location     [1] OCTET STRING	OPTIONAL,
    -- raw copy of the location string from the P-Access-Network-Info header
    location          [2] Location     	OPTIONAL,
    
    ...
}


PartyInformation 			::= SEQUENCE 
{
	party-Qualifier 	[0]  ENUMERATED 
	{
		gPRS-Target(3),
		...
	},
	partyIdentity 		[1] SEQUENCE 
	{
		imei					[1] OCTET STRING (SIZE (8)) OPTIONAL,
			-- See MAP format [4]

		imsi					[3] OCTET STRING (SIZE (3..8)) OPTIONAL,
			-- See MAP format [4] International Mobile 
			-- Station Identity E.212 number beginning with Mobile Country Code

		msISDN					[6] OCTET STRING (SIZE (1..9)) OPTIONAL,
			-- MSISDN of the target, encoded in the same format as the AddressString
			-- parameters defined in MAP format document TS 29.002 [4]

		e164-Format				[7] OCTET STRING    (SIZE (1 .. 25)) OPTIONAL,
			-- E164 address of the node in international format. Coded in the same format as 
			-- the calling party number  parameter of the ISUP (parameter part:[29])

		sip-uri					[8] OCTET STRING 	OPTIONAL,
			-- See [26]

		...,
		tel-uri					[9] OCTET STRING 	OPTIONAL,
			-- See [67]
		x-3GPP-Asserted-Identity [10] OCTET STRING 	OPTIONAL,	
		-- X 3GPP Asserted Identity header (3GPP TS 24 109 [79]) of the target, used in 
		-- some XCAP transactions. This information complement SIP URI or Tel URI of the target.
		xUI						[11] OCTET STRING 	OPTIONAL
		-- XCAP User Identifier (XUI)is a string, valid as a path element in an XCAP URI, that 
		-- may be associated with each user served by a XCAP resource server. Defined in IETF 
		-- RFC 4825[80]. This information may complement SIP URI or Tel URI of the target.

	},

	services-Data-Information 	[4] Services-Data-Information OPTIONAL,
		-- This parameter is used to transmit all the information concerning the
		-- complementary information associated to the basic data call
	...
}

Location	::= SEQUENCE 
{
	e164-Number         [1] OCTET STRING (SIZE (1..25)) OPTIONAL,
        -- Coded in the same format as the ISUP location number (parameter
        -- field) of the ISUP (see EN 300 356 [30]).    
	globalCellID		[2] GlobalCellID	OPTIONAL,
		--see MAP format (see [4])	
	rAI					[4] Rai		OPTIONAL,
		-- the Routeing Area Identifier in the current  SGSN is coded in accordance with the 
		-- § 10.5.5.15 of document [9] without the Routing Area Identification IEI  
		-- (only the last 6 octets are used)
	gsmLocation			[5] GSMLocation OPTIONAL,
 	umtsLocation		[6] UMTSLocation OPTIONAL,
	sAI					[7] Sai	OPTIONAL,
		-- format:	PLMN-ID	3 octets (no. 1 - 3)
		--			LAC		2 octets (no. 4 - 5)
		--			SAC		2 octets (no. 6 - 7)
		--			(according to 3GPP TS 25.413 [62])
	...,
	oldRAI				[8] Rai		OPTIONAL,
		-- the Routeing Area Identifier in the old SGSN is coded in accordance with the 
		-- § 10.5.5.15 of document [9] without the Routing Area Identification IEI 
		-- (only the last 6 octets are used). 
	tAI					[9] OCTET STRING (SIZE (6))	OPTIONAL,
		-- The TAI is coded according to the TS 29.118 [64] without the TAI IEI.
		-- The tAI parameter is applicable only to the CS traffic cases where 
		-- the available location information is the one received from the the MME. 
	eCGI				[10] OCTET STRING (SIZE (8)) OPTIONAL,
		-- the ECGI is coded according to the TS 29.118 [64] without the ECGI IEI.
		-- The eCGI parameter is applicable only to the CS traffic cases where 
		-- the available location information is the one received from the the MME.
	civicAddress		[11] CivicAddress OPTIONAL
		-- Every elements that describe civicAddress are based on IETF RFC 4776 or IETF
		-- 5139, ISO.3166-1 and -2, ISO 639-1, UPU SB42-4 ([71]to [75]) Such element is to
		-- enrich IRI
		-- Messages to LEMF by civic elements on the location of a H(e)NodeB or a WLAN hotspot,
		-- instead of geographical location  of the target or any geo-coordinates. Please, look
		-- at the §5.11 location information of TS 33 106 and §4 functional architecture of TS
		-- 33.107 on how such element can be used. 
}

GlobalCellID	::= OCTET STRING  (SIZE (5..7))
Rai				::= OCTET STRING (SIZE (6))
Sai				::=	OCTET STRING (SIZE (7))

GSMLocation 	::= CHOICE 
{
	geoCoordinates 	[1] SEQUENCE	
	{
		latitude		[1]	PrintableString (SIZE(7..10)),
							-- format : 	XDDMMSS.SS
		longitude		[2]	PrintableString (SIZE(8..11)),
							-- format : 	XDDDMMSS.SS
		mapDatum		[3]	MapDatum DEFAULT wGS84,
		...,
		azimuth			[4] INTEGER (0..359) OPTIONAL
			-- The azimuth is the bearing, relative to true north.
	},
		-- format : 	XDDDMMSS.SS
		-- 				X 			: N(orth), S(outh), E(ast), W(est)
		--				DD or DDD 	: degrees (numeric characters)
		--				MM			: minutes (numeric characters)
		--				SS.SS 		: seconds, the second part (.SS) is optionnal
		-- Example :
		--			latitude short form		N502312
		--			longitude long form		E1122312.18

	utmCoordinates	[2] SEQUENCE	
	{
		utm-East 		[1] PrintableString (SIZE(10)),		
		utm-North 		[2] PrintableString (SIZE(7)),	
			-- example	utm-East	32U0439955
			--			utm-North	5540736
		mapDatum		[3]	MapDatum DEFAULT wGS84,
		...,
		azimuth			[4] INTEGER (0..359) OPTIONAL
			-- The azimuth is the bearing, relative to true north.
 	},

	utmRefCoordinates  	[3] SEQUENCE 
	{
		utmref-string		PrintableString (SIZE(13)),
		mapDatum			MapDatum DEFAULT wGS84,
		...
	},
		-- example	32UPU91294045		

	wGS84Coordinates  	[4] OCTET STRING
		-- format is as defined in [37].
}

MapDatum ::= ENUMERATED
{	
	wGS84,
	wGS72,
	eD50, 	-- European Datum 50
	...
}

UMTSLocation ::= CHOICE {
	point					[1]	GA-Point,
	pointWithUnCertainty	[2]	GA-PointWithUnCertainty,
	polygon					[3]	GA-Polygon
}

GeographicalCoordinates ::= SEQUENCE {
	latitudeSign			ENUMERATED { north, south },
	latitude				INTEGER (0..8388607),
	longitude				INTEGER (-8388608..8388607),
	...
}

GA-Point ::= SEQUENCE {
	geographicalCoordinates		GeographicalCoordinates,
	...
}

GA-PointWithUnCertainty ::=SEQUENCE {
	geographicalCoordinates		GeographicalCoordinates,
	uncertaintyCode				INTEGER (0..127)
}

maxNrOfPoints						INTEGER ::= 15

GA-Polygon ::= SEQUENCE (SIZE (1..maxNrOfPoints)) OF
	SEQUENCE {
		geographicalCoordinates		GeographicalCoordinates,
		...
	}

CivicAddress ::= CHOICE { 
    detailedCivicAddress        SET OF DetailedCivicAddress, 
	xmlCivicAddress				XmlCivicAddress, 
	...
}

XmlCivicAddress ::= UTF8String 
     -- Must conform to the February 2008 version of the XML format on the representation of 
     -- civic location described in IETF RFC 5139[yy].


DetailedCivicAddress ::= SEQUENCE {
	building			[1] UTF8String OPTIONAL,
		-- Building (structure), for example Hope Theatre
	room				[2] UTF8String OPTIONAL,
		-- Unit (apartment, suite), for example 12a
	placeType			[3] UTF8String OPTIONAL,
		-- Place-type, for example office
	postalCommunityName	[4] UTF8String OPTIONAL,
		-- Postal Community Name, for example Leonia
	additionalCode	[5] UTF8String OPTIONAL,
		-- Additional Code, for example 13203000003
	seat				[6] UTF8String OPTIONAL,
		-- Seat, desk, or cubicle, workstation, for example WS 181
	primaryRoad		[7] UTF8String OPTIONAL,
		-- RD is the primary road name, for example Broadway
	primaryRoadDirection   [8] UTF8String OPTIONAL,
		-- PRD is the leading road direction, for example N or North
	trailingStreetSuffix [9] UTF8String OPTIONAL,
		-- POD or trailing street suffix, for example SW or South West
	streetSuffix		[10] UTF8String OPTIONAL,
		-- Street suffix or type, for example Avenue or Platz or Road
	houseNumber			[11] UTF8String OPTIONAL,
		-- House number, for example 123
	houseNumberSuffix	[12] UTF8String OPTIONAL,
		-- House number suffix, for example A or Ter
	landmarkAddress		[13] UTF8String OPTIONAL, 
		-- Landmark or vanity address, for example Columbia University
	additionalLocation	[114] UTF8String OPTIONAL,
		-- Additional location, for example South Wing
	name 			[15] UTF8String OPTIONAL, 
		-- Residence and office occupant, for example Joe"s Barbershop
	floor 			[16] UTF8String OPTIONAL, 
		-- Floor, for example 4th floor
	primaryStreet	[17] UTF8String OPTIONAL, 
		-- Primary street name, for example Broadway 
	primaryStreetDirection   [18] UTF8String OPTIONAL,
		-- PSD is the leading street direction, for example N or North
	roadSection		[19] UTF8String OPTIONAL, 
		-- Road section, for example 14
	roadBranch    	[20] UTF8String OPTIONAL, 
		-- Road branch, for example Lane 7
	roadSubBranch  	[21] UTF8String OPTIONAL, 
		-- Road sub-branch, for example Alley 8
	roadPreModifier [22] UTF8String OPTIONAL, 
		-- Road pre-modifier, for example Old
	roadPostModifier [23] UTF8String OPTIONAL,   
		-- Road post-modifier, for example Extended
	postalCode		[24]UTF8String OPTIONAL, 
		-- Postal/zip code, for example 10027-1234
	town			[25] UTF8String OPTIONAL, 
	county			[26] UTF8String OPTIONAL, 
		-- An administrative sub-section, often defined in ISO.3166-2[74]  International
		-- Organization for Standardization, "Codes for the representation of names of
		-- countries and their subdivisions -  Part 2: Country subdivision code"
	country			[27] UTF8String,
		-- Defined in ISO.3166-1 [39] International Organization for Standardization, "Codes for
		-- the representation of names of countries and their subdivisions - Part 1: Country
		-- codes". Such definition is not optional in case of civic address. It is the
		-- minimum information needed to qualify and describe a civic address, when a
		-- regulation of a specific country requires such information
	language		[28] UTF8String, 
		-- Language defined in the IANA registry according to the assignments found
		-- in the standard ISO 639 Part 1, "ISO 639-1:2002[75], Codes for the representation of
		-- names of languages - Part 1: Alpha-2 code" or using assignments subsequently made
		-- by the ISO 639 Part 1 maintenance agency
	...
}

SMS-report		::= SEQUENCE 
{
	sMS-Contents	[3] SEQUENCE
	{
		sms-initiator		[1] ENUMERATED 	-- party which sent the  SMS
		{
			target			(0),
			server			(1), 
			undefined-party	(2),
			...
		},
		transfer-status		[2] ENUMERATED 
		{
			succeed-transfer	(0), 		-- the transfer of the SMS message succeeds
			not-succeed-transfer(1), 
			undefined			(2),
			... 
		} OPTIONAL,
		other-message		[3] ENUMERATED 	-- in case of terminating call, indicates if
											-- the server will send other SMS
		{
			yes			(0),
			no			(1), 
			undefined	(2),
			... 
		} OPTIONAL,
		content				[4] OCTET STRING (SIZE (1 .. 270)) OPTIONAL,
									-- Encoded in the format defined for the SMS mobile 
		... 
	}	
}

GPRSCorrelationNumber ::= OCTET STRING (SIZE(8..20))
CorrelationValues ::= CHOICE {
		
		iri-to-CC 	[0]		IRI-to-CC-Correlation, -- correlates IRI to Content(s)
		iri-to-iri	[1]		IRI-to-IRI-Correlation, -- correlates IRI to IRI 
		both-IRI-CC	[2]		SEQUENCE { -- correlates IRI to IRI and IRI to Content(s)
								iri-CC	[0]	IRI-to-CC-Correlation,
								iri-IRI	[1]	IRI-to-IRI-Correlation}
}
 
 
IMS-VoIP-Correlation ::= SET OF SEQUENCE {
			ims-iri		[0]		IRI-to-IRI-Correlation,
			ims-cc		[1]		IRI-to-CC-Correlation 		OPTIONAL
}

IRI-to-CC-Correlation ::= SEQUENCE { -- correlates IRI to Content
			cc 		[0] SET OF 	OCTET STRING,-- correlates IRI to multiple CCs
			iri 	[1] 		OCTET STRING OPTIONAL 
									-- correlates IRI to CC with signaling
}
IRI-to-IRI-Correlation ::= OCTET STRING -- correlates IRI to IRI


GPRSEvent ::= ENUMERATED 
{
	pDPContextActivation 					(1),
	startOfInterceptionWithPDPContextActive	(2),
	pDPContextDeactivation					(4),
	gPRSAttach 								(5),
	gPRSDetach 								(6),
	locationInfoUpdate 						(10),
	sMS 									(11),
	pDPContextModification					(13),
	servingSystem							(14),
	... ,
	startOfInterceptionWithMSAttached		(15) ,
	packetDataHeaderInformation				(16)

}
-- see [19]

IMSevent ::= ENUMERATED 
{
	unfilteredSIPmessage (1),
		-- This value indicates to LEMF that the whole SIP message is sent , i.e. without filtering
        -- CC; location information is removed by the DF2/MF if not required to be sent.

	...,
	sIPheaderOnly (2),
		-- If warrant requires only IRI then specific content in a 'sIPMessage'
		-- (e.g. 'Message', etc.) has been deleted before sending it to LEMF.

    decryptionKeysAvailable (3) ,
		-- This value indicates to LEMF that the IRI carries CC decryption keys for the session
        -- under interception. 

    startOfInterceptionForIMSEstablishedSession  (4) ,
        -- This value indicates to LEMF that the IRI carries information related to
                -- interception started on an already established IMS session. 
	xCAPRequest (5),
		-- This value indicates to LEMF that the XCAP request is sent.
	xCAPResponse (6)
		-- This value indicates to LEMF that the XCAP response is sent.

}

Services-Data-Information ::= SEQUENCE
{
	gPRS-parameters [1] GPRS-parameters OPTIONAL,
	...
}

GPRS-parameters ::= SEQUENCE 
{
	pDP-address-allocated-to-the-target 	[1] DataNodeAddress OPTIONAL,
	aPN 					[2] OCTET STRING (SIZE(1..100)) OPTIONAL,
	-- The Access Point Name (APN) is coded in accordance with
		-- 3GPP TS 24.008 [9] without the APN IEI (only the last 100 octets are used).
		-- Octets are coded according to 3GPP TS 23.003 [25].
	pDP-type 				[3] OCTET STRING (SIZE(2)) OPTIONAL, 
    -- Include either Octets 3 and 4 of the Packet Data Protocol Address information element of 
    -- 3GPP TS 24.008 [9]or Octets 4 and 5 of the End User Address IE of 3GPP TS 29.060 [17].

	-- when PDP-type is IPv4 or IPv6, the IP address is carried by parameter
	-- pDP-address-allocated-to-the-target
	-- when PDP-type is IPv4v6, the additional IP address is carried by parameter
	-- additionalIPaddress
	...,
	nSAPI					[4] OCTET STRING (SIZE (1)) OPTIONAL,
    -- Include either Octet 2 of the NSAPI IE of 3GPP TS 24.008 [9] or Octet 2 of the NSAPI IE of 
    -- 3GPP TS 29.060 [17].
	additionalIPaddress		[5] DataNodeAddress OPTIONAL
}

GPRSOperationErrorCode ::= OCTET STRING
-- The parameter shall carry the GMM cause value or the SM cause value, as defined in the
-- standard [9], without the IEI.


LDIevent ::= ENUMERATED 
{
	targetEntersIA 			(1),
	targetLeavesIA			(2),
	...
}

UmtsQos ::= CHOICE
{
	qosMobileRadio [1] OCTET STRING,
		-- The qosMobileRadio parameter shall be coded in accordance with the § 10.5.6.5 of
		-- document [9] without the Quality of service IEI and Length of 
		-- quality of service IE (. That is, first 
		-- two octets carrying 'Quality of service IEI' and 'Length of quality of service
 		-- IE' shall be excluded). 
	qosGn [2] OCTET STRING
		-- qosGn parameter shall be coded in accordance with § 7.7.34 of document [17]
} 

MediaDecryption-info ::= SEQUENCE OF CCKeyInfo
		-- One or more key can be available for decryption, one for each media streams of the
        -- intercepted session.

CCKeyInfo ::= SEQUENCE
{
	cCCSID	 [1]	OCTET STRING,	
		-- the parameter uniquely mapping the key to the encrypted stream. 
	cCDecKey [2]	OCTET STRING,
	cCSalt   [3]    OCTET STRING OPTIONAL,
        -- The field reports the value from the CS_ID field in the ticket exchange headers as
        -- defined in IETF RFC 6043 [61].
	...
}

MediaSecFailureIndication  ::= ENUMERATED
{
    genericFailure  (0),
    ...
}
 

PacketDataHeaderInformation ::= CHOICE
{

	packetDataHeader		[1]	PacketDataHeader,
	packetDataHeaderSummary	[2]	PacketDataHeaderSummary,
...
}

PacketDataHeader ::= CHOICE
{

	packetDataHeaderMapped	[1]	PacketDataHeaderMapped,
	packetDataHeaderCopy	[2]	PacketDataHeaderCopy,
...
}

PacketDataHeaderMapped ::= SEQUENCE 
{
	sourceIPAddress			[1] IPAddress,
	sourcePortNumber		[2] INTEGER (0..65535) OPTIONAL,	
	destinationIPAddress	[3] IPAddress,
	destinationPortNumber	[4] INTEGER (0..65535) OPTIONAL,
	transportProtocol		[5] INTEGER,
	-- For IPv4, report the 'Protocol' field and for IPv6 report 'Next Header' field.
	-- Assigned Internet Protocol Numbers can be found at 
	-- http://www.iana.org/assignments/protocol-numbers/protocol-numbers.xml
	packetsize				[6] INTEGER OPTIONAL,
	flowLabel				[7] INTEGER OPTIONAL,
	packetCount				[8] INTEGER OPTIONAL,
	direction				[9] TPDU-direction,
...
} 


TPDU-direction ::= ENUMERATED
{
	from-target 	(1),
	to-target 		(2),
	unknown 		(3)
}

PacketDataHeaderCopy ::= SEQUENCE 
{
	direction				[1] TPDU-direction,
	headerCopy				[2] OCTET STRING,	-- includes a copy of the packet header at the IP 
				-- network layer and above including extension headers, but excluding contents.
...
} 


PacketDataHeaderSummary ::= SEQUENCE OF PacketFlowSummary

PacketFlowSummary ::= SEQUENCE
{

	sourceIPAddress			[1] IPAddress,
	sourcePortNumber		[2] INTEGER (0..65535) OPTIONAL,	
	destinationIPAddress	[3] IPAddress,
	destinationPortNumber	[4] INTEGER (0..65535) OPTIONAL,
	transportProtocol		[5] INTEGER,
	-- For IPv4, report the 'Protocol' field and for IPv6 report 'Next Header' field.
	-- Assigned Internet Protocol Numbers can be found at 
	-- http://www.iana.org/assignments/protocol-numbers/protocol-numbers.xml
	flowLabel				[6] INTEGER OPTIONAL,
	summaryPeriod			[7] ReportInterval,
	packetCount				[8] INTEGER,
	sumOfPacketSizes		[9] INTEGER, 
	packetDataSummaryReason	[10] ReportReason, 
...
}
	
 

ReportReason ::= ENUMERATED
{
	timerExpired			(0),	
	countThresholdHit		(1),
	pDPComtextDeactivated   (2),
	pDPContextModification	(3),
	otherOrUnknown		(4),
	...
} 

ReportInterval ::= SEQUENCE
{
	firstPacketTimeStamp	[0] TimeStamp,
	lastPacketTimeStamp		[1] TimeStamp,
	...
} 

END -- OF UmtsHI2Operations
 



-- Source: UmtsCS-HI2Operations,rel12.txt 
-- ETSI TS 133 108 V12.11.0 (2016-01)
-- B.3a	Interception related information (HI2 CS)
UmtsCS-HI2Operations 
{itu-t (0) identified-organization (4) etsi (0) securityDomain (2) lawfulIntercept (2) threeGPP(4) hi2CS (3) r11(11) version-1 (1)} 

DEFINITIONS IMPLICIT TAGS ::=

BEGIN

IMPORTS OPERATION, 
	ERROR 
		FROM Remote-Operations-Information-Objects 
		{joint-iso-itu-t (2) remote-operations(4) informationObjects(5) version1(0)}

	LawfulInterceptionIdentifier,
	TimeStamp,
	Intercepted-Call-State,
	PartyInformation,
	CallContentLinkCharacteristics,
	CommunicationIdentifier,
	CC-Link-Identifier,
	National-Parameters,
	National-HI2-ASN1parameters

	FROM HI2Operations
		{itu-t(0) identified-organization(4) etsi(0) securityDomain(2)
			lawfulIntercept(2) hi2(1) version9(9)} -- Imported from TS 101 671v2.13.1

	Location,
	SMS-report

	FROM UmtsHI2Operations
		{itu-t(0) identified-organization(4) etsi(0) securityDomain(2)
			lawfulintercept(2) threeGPP(4) hi2(1) r11(11) version-0(0)};


-- Object Identifier Definitions

-- Security DomainId
lawfulInterceptDomainId OBJECT IDENTIFIER ::= {itu-t(0) identified-organization(4) etsi(0)
securityDomain(2) lawfulIntercept(2)}

-- Security Subdomains
threeGPPSUBDomainId OBJECT IDENTIFIER ::= {lawfulInterceptDomainId threeGPP(4)}
hi2CSDomainId OBJECT IDENTIFIER ::= {threeGPPSUBDomainId hi2CS(3) r11(11) version-1(1)}


umtsCS-sending-of-IRI  OPERATION ::= 
{
	ARGUMENT	UmtsCS-IRIsContent
	ERRORS		{ OperationErrors }
	CODE		global:{ threeGPPSUBDomainId hi2CS(3) opcode(1)}
}
-- Class 2 operation. The timer shall be set to a value between 3 s and 240 s. 
-- The timer.default value is 60s.
-- NOTE: The same note as for HI management operation applies.

UmtsCS-IRIsContent		::= CHOICE
{
	iRIContent			UmtsCS-IRIContent,
	iRISequence			UmtsCS-IRISequence
}

UmtsCS-IRISequence		::= SEQUENCE OF UmtsCS-IRIContent
	-- Aggregation of UmtsCS-IRIContent is an optional feature.
	-- It may be applied in cases when at a given point in time several IRI records are 
	-- available for delivery to the same LEA destination.
	-- As a general rule, records created at any event shall be sent immediately and shall 
	-- not held in the DF or MF in order to apply aggregation. 
-- When aggregation is not to be applied, UmtsCS-IRIContent needs to be chosen.
		
UmtsCS-IRIContent		::= CHOICE 
{
	iRI-Begin-record		[1] IRI-Parameters,
		--at least one optional parameter must be included within the iRI-Begin-Record
	iRI-End-record			[2] IRI-Parameters,
	iRI-Continue-record		[3] IRI-Parameters,
		--at least one optional parameter must be included within the iRI-Continue-Record
	iRI-Report-record		[4] IRI-Parameters,
		--at least one optional parameter must be included within the iRI-Report-Record
	...
}

unknown-version 		ERROR ::= { CODE local:0}
missing-parameter		ERROR ::= { CODE local:1}
unknown-parameter-value	ERROR ::= { CODE local:2}
unknown-parameter		ERROR ::= { CODE local:3}

OperationErrors ERROR ::= 
{ 
	unknown-version | 
	missing-parameter | 
	unknown-parameter-value | 
	unknown-parameter 
}
--These values may be sent by the LEMF, when an operation or a parameter is misunderstood.

IRI-Parameters		::= SEQUENCE 
{
	hi2CSDomainId						[0]	OBJECT IDENTIFIER, -- 3GPP HI2 CS domain

	iRIversion							[23] ENUMERATED
	{
		version1(1),
		...,
		version2(2),
		version3(3),
		-- versions 4-7 were ommited to align with UmtsHI2Operations.
		lastVersion(8)
	} OPTIONAL,
		-- Optional parameter "iRIversion" (tag 23) was always redundant in 33.108, because 
		-- the object identifier "hi2CSDomainId" was introduced into "IRI Parameters" with the 
		-- initial HI2 CS domain module in 33.108v6.1.0. In order to keep backward compatibility, 
		-- even when the version of the "hi2CSDomainId" parameter will be incremented it is 
		-- recommended to always send to LEMF the same: enumeration value "lastVersion(8)".
		-- if not present, it means version 1 is handled
	lawfulInterceptionIdentifier		[1] LawfulInterceptionIdentifier,
		-- This identifier is associated to the target.
	communicationIdentifier				[2] CommunicationIdentifier,
		-- used to uniquely identify an intercepted call.

	timeStamp							[3] TimeStamp, 
		-- date and time of the event triggering the report.
	intercepted-Call-Direct 			[4] ENUMERATED 
	{
		not-Available(0),
		originating-Target(1),
		terminating-Target(2),
	...
	} OPTIONAL,
	intercepted-Call-State 				[5] Intercepted-Call-State OPTIONAL,
		-- Not required for UMTS. May be included for backwards compatibility to GSM	ringingDuration 					[6] OCTET STRING (SIZE (3)) OPTIONAL,
		-- Duration in seconds. BCD coded : HHMMSS
		-- Not required for UMTS. May be included for backwards compatibility to GSM	conversationDuration 				[7] OCTET STRING (SIZE (3)) OPTIONAL,
		-- Duration in seconds. BCD coded : HHMMSS
		-- Not required for UMTS. May be included for backwards compatibility to GSM
	locationOfTheTarget					[8] Location OPTIONAL,
		-- location of the target 
	partyInformation 					[9] SET SIZE (1..10) OF PartyInformation OPTIONAL, 
		-- This parameter provides the concerned party (Originating, Terminating or forwarded
		-- party), the identity(ies) of the party and all the information provided by the party. 
	callContentLinkInformation			[10] SEQUENCE 
	{
		cCLink1Characteristics		[1] CallContentLinkCharacteristics OPTIONAL,
			-- information concerning the Content of Communication Link Tx channel established
			-- toward the LEMF (or the sum signal channel, in case of mono mode).
		cCLink2Characteristics		[2] CallContentLinkCharacteristics OPTIONAL,
			-- information concerning the Content of Communication Link Rx channel established
			-- toward the LEMF.
		... 
	} OPTIONAL,
	release-Reason-Of-Intercepted-Call	[11] OCTET STRING (SIZE (2)) OPTIONAL,
		-- Release cause coded in [31] format. 
		-- This parameter indicates the reason why the
		-- intercepted call cannot be established or why the intercepted call has been
		-- released after the active phase.
	nature-Of-The-intercepted-call		[12] ENUMERATED 
	{
		--Not required for UMTS. May be included for backwards compatibility to GSM
		--Nature of the intercepted "call":
		gSM-ISDN-PSTN-circuit-call(0),
			-- the possible UUS content is sent through the HI2 or HI3 "data" interface
			-- the possible call content call is established through the HI3 „circuit„ interface
		gSM-SMS-Message(1),
			-- the SMS content is sent through the HI2 or HI3 "data" interface
		uUS4-Messages(2),
			-- the UUS content is sent through the HI2 or HI3 "data" interface
		tETRA-circuit-call(3),
			-- the possible call content call is established through the HI3 "circuit" interface
			-- the possible data are sent through the HI3 "data" interface
		teTRA-Packet-Data(4),
			-- the data are sent through the HI3 "data" interface
		gPRS-Packet-Data(5),
			-- the data are sent through the HI3 "data" interface
		...
	} OPTIONAL,
	serviceCenterAddress				[13] PartyInformation OPTIONAL,
		-- e.g. in case of SMS message this parameter provides the address of  the relevant 
		-- server within the calling (if server is originating) or called 
		-- (if server is terminating) party address parameters
	sMS									[14] SMS-report OPTIONAL,
		-- this parameter provides the SMS content and associated information
	cC-Link-Identifier					[15] CC-Link-Identifier OPTIONAL,
		-- Depending on a network option, this parameter may be used to identify a CC link
		-- in case of multiparty calls.
	national-Parameters					[16] National-Parameters OPTIONAL,
	...,
	umts-Cs-Event						[33] Umts-Cs-Event OPTIONAL,
	-- Care should be taken to ensure additional parameter numbering does not conflict with
	-- ETSI TS 101 671 or Annex B.3 of this document (PS HI2).
	national-HI2-ASN1parameters			[255]	National-HI2-ASN1parameters	OPTIONAL

}

Umts-Cs-Event ::= ENUMERATED
{
	call-establishment				(1),
	answer							(2),
	supplementary-Service			(3),
	handover						(4),
	release							(5),
	sMS								(6),
	location-update					(7),
	subscriber-Controlled-Input 	(8),
	...
}

END -- OF UmtsCS-HI2Operations




-- Source: EpsHI2Operations,rel12.txt
-- ETSI TS 133 108 V12.11.0 (2016-01)
-- Annex B.9	Intercept related information (HI2 SAE/EPS and IMS)
EpsHI2Operations {itu-t(0) identified-organization(4) etsi(0) securityDomain(2) lawfulintercept(2) threeGPP(4) hi2eps(8) r12(12) version-60 (60)} 

DEFINITIONS IMPLICIT TAGS ::=

BEGIN

IMPORTS 

		OPERATION, 
		ERROR 
			FROM Remote-Operations-Information-Objects 
			{joint-iso-itu-t(2) remote-operations(4) informationObjects(5) version1(0)}

		LawfulInterceptionIdentifier,
		TimeStamp,
		Network-Identifier,
		National-Parameters,
		National-HI2-ASN1parameters,
		DataNodeAddress,
		IPAddress,
		IP-value,
		X25Address

			FROM HI2Operations
			{itu-t(0) identified-organization(4) etsi(0) securityDomain(2)
 				  lawfulIntercept(2) hi2(1) version18(18)} -- Imported from TS 101 671v3.12.1
		
  		CivicAddress

			FROM UmtsHI2Operations
    		{itu-t(0) identified-organization(4) etsi(0) securityDomain(2)
   				lawfulintercept(2) threeGPP(4) hi2(1) r12(12) version-8 (8)};
    			-- Imported from 3GPP TS 33.108, UMTS PS HI2
	

-- Object Identifier Definitions

-- Security DomainId
lawfulInterceptDomainId OBJECT IDENTIFIER ::= {itu-t(0) identified-organization(4) etsi(0)
securityDomain(2) lawfulIntercept(2)}

-- Security Subdomains
threeGPPSUBDomainId OBJECT IDENTIFIER ::= {lawfulInterceptDomainId threeGPP(4)}
hi2epsDomainId OBJECT IDENTIFIER	::= {threeGPPSUBDomainId hi2eps(8) r12(12) version-60 (60)}

eps-sending-of-IRI  OPERATION ::= 
{
	ARGUMENT	EpsIRIsContent
	ERRORS		{ OperationErrors }
	CODE		global:{threeGPPSUBDomainId hi2eps(8) opcode(1)}
}
-- Class 2 operation . The timer shall be set to a value between 3 s and 240 s. 
-- The timer.default value is 60s.
-- NOTE:	The same note as for HI management operation applies.

EpsIRIsContent		::= CHOICE
{
	epsiRIContent			EpsIRIContent,
	epsIRISequence			EpsIRISequence
}

EpsIRISequence		::= SEQUENCE OF EpsIRIContent

-- Aggregation of EpsIRIContent is an optional feature.
-- It may be applied in cases when at a given point in time
-- several IRI records are available for delivery to the same LEA destination.
-- As a general rule, records created at any event shall be sent
-- immediately and not withheld in the DF or MF in order to
-- apply aggragation.
-- When aggregation is not to be applied,  
-- EpsIRIContent needs to be chosen. 
-- EpsIRIContent includes events that correspond to EPS and UMTS/GPRS.  


EpsIRIContent		::= CHOICE 
{
	iRI-Begin-record		[1] IRI-Parameters,	-- include at least one optional parameter 
	iRI-End-record			[2] IRI-Parameters,
	iRI-Continue-record		[3] IRI-Parameters,	-- include at least one optional parameter 
	iRI-Report-record		[4] IRI-Parameters	-- include at least one optional parameter 
}
-- the EpsIRIContent may provide events that correspond to UMTS/GPRS as well.

unknown-version 		ERROR ::= { CODE local:0}
missing-parameter		ERROR ::= { CODE local:1}
unknown-parameter-value	ERROR ::= { CODE local:2}
unknown-parameter		ERROR ::= { CODE local:3}

OperationErrors ERROR ::= 
{ 
	unknown-version | 
	missing-parameter | 
	unknown-parameter-value | 
	unknown-parameter 
}
-- These values may be sent by the LEMF, when an operation or a parameter is misunderstood.

-- Parameters having the same tag numbers must be identical in Rel-5 and onwards modules.
IRI-Parameters		::= SEQUENCE 
{
	hi2epsDomainId				[0]	OBJECT IDENTIFIER,  -- 3GPP HI2 EPS domain
	lawfulInterceptionIdentifier	[1] LawfulInterceptionIdentifier,
		-- This identifier is associated to the target.
	timeStamp				[3] TimeStamp, 
		-- date and time of the event triggering the report.) 
	initiator 				[4] ENUMERATED 
	{
		not-Available		(0),
		originating-Target	(1),
			-- in case of GPRS, this indicates that the PDP context activation, modification 
			-- or deactivation is MS requested
			-- in case of EPS, this indicated that the EPS detach, bearer activation, modification 
			-- or deactivation is UE requested
		terminating-Target	(2),
			-- in case of GPRS, this indicates that the PDP context activation, modification or
			-- deactivation is network initiated
			-- in case of EPS, this indicated that the EPS detach, bearer activation, modification
			-- or deactivation is network initiated
	...
	} OPTIONAL,

	locationOfTheTarget		[8] Location OPTIONAL,
		-- location of the target 
	partyInformation 		[9] SET SIZE (1..10) OF PartyInformation OPTIONAL, 
		-- This parameter provides the concerned party, the identiy(ies) of the party
		--)and all the information provided by the party. 

	serviceCenterAddress	[13] PartyInformation OPTIONAL,
		-- e.g. in case of SMS message this parameter provides the address of  the relevant 
		-- server within the calling (if server is originating) or called (if server is
		-- terminating) party address parameters
	sMS						[14] SMS-report OPTIONAL,
		-- this parameter provides the SMS content and associated information

	national-Parameters		[16] National-Parameters OPTIONAL,
	ePSCorrelationNumber	[18] EPSCorrelationNumber OPTIONAL, 
		-- this parameter provides GPRS Correlation number when the event corresponds to UMTS/GPRS.
	ePSevent 				[20] EPSEvent OPTIONAL,
		-- This information is used to provide particular action of the target
		-- such as attach/detach
	sgsnAddress 			[21] DataNodeAddress OPTIONAL,
	gPRSOperationErrorCode 	[22] GPRSOperationErrorCode OPTIONAL,
	ggsnAddress 			[24] DataNodeAddress OPTIONAL,
	qOS						[25] UmtsQos OPTIONAL,
	networkIdentifier		[26] Network-Identifier OPTIONAL,
	sMSOriginatingAddress 	[27] DataNodeAddress OPTIONAL,
	sMSTerminatingAddress 	[28] DataNodeAddress OPTIONAL,
	iMSevent				[29] IMSevent OPTIONAL,
	sIPMessage				[30] OCTET STRING  OPTIONAL,
	servingSGSN-number		[31] OCTET STRING (SIZE (1..20))	OPTIONAL,
	servingSGSN-address		[32] OCTET STRING (SIZE (5..17)) 	OPTIONAL,
								-- Octets are coded according to 3GPP TS 23.003 [25]
	..., 
 			-- Tag			[33] was taken into use by ETSI module in TS 101 671v2.13.1
	ldiEvent	 			[34] LDIevent OPTIONAL,
	correlation 			[35] CorrelationValues OPTIONAL,
    ePS-GTPV2-specificParameters   [36] EPS-GTPV2-SpecificParameters OPTIONAL,
         -- contains parameters to be used in case of GTPV2 based intercepted messages
    ePS-PMIP-specificParameters    [37] EPS-PMIP-SpecificParameters OPTIONAL,
         -- contains parameters to be used in case of PMIP based intercepted messages
    ePS-DSMIP-SpecificParameters   [38] EPS-DSMIP-SpecificParameters OPTIONAL,
         -- contains parameters to be used in case of DSMIP based intercepted messages
    ePS-MIP-SpecificParameters     [39] EPS-MIP-SpecificParameters OPTIONAL,
         -- contains parameters to be used in case of MIP based intercepted messages
    servingNodeAddress             [40] OCTET STRING               OPTIONAL,
         -- this parameter is kept for backward compatibility only and should not be used
         -- as it has been superseeded by parameter visitedNetworkId
    visitedNetworkId               [41] UTF8String                 OPTIONAL,
         -- contains the visited network identifier inside the EPS Serving System Update for
         -- non 3GPP access, coded according to [53]

	mediaDecryption-info	       [42] MediaDecryption-info OPTIONAL, 
	servingS4-SGSN-address	       [43] OCTET STRING OPTIONAL,
	-- Diameter Origin-Host and Origin-Realm of the S4-SGSN based on the TS 29.272 [59]. 
	-- Only the data fields from the Diameter AVPs are provided concatenated 
	-- with a semicolon to populate this field. 

    sipMessageHeaderOffer   [44] OCTET STRING OPTIONAL,
    sipMessageHeaderAnswer  [45] OCTET STRING OPTIONAL,
    sdpOffer                [46] OCTET STRING OPTIONAL,
    sdpAnswer               [47] OCTET STRING OPTIONAL, 
    uLITimestamp            [48] OCTET STRING (SIZE (8)) OPTIONAL,
    -- Coded according to 3GPP TS 29.060 [17]; Only the ULI Timestamp value is reported. 
	packetDataHeaderInformation		   [49] PacketDataHeaderInformation	OPTIONAL, 
    mediaSecFailureIndication          [50] MediaSecFailureIndication OPTIONAL,
	csgIdentity			[51] OCTET STRING (SIZE (4)) OPTIONAL,  -- Octets are coded 
      -- according to 3GPP TS 23.003 [25].  The 27 bits specified in TS 23.003 shall be encoded as. 
      -- follows The most significant bit of the CSG Identity shall be encoded in the most 
      -- significant bit of the first octet of the octet string and the least significant bit coded 
      -- in bit 6 of octet 4.
	heNBIdentity			[52] OCTET STRING OPTIONAL, 
      -- 4 or 6 octets are coded with the HNBUnique Identity       
	  -- as specified in 3GPP TS 23.003            [25], Clause 4.10.
	heNBiPAddress		[53] IPAddress  OPTIONAL,
	heNBLocation			[54] HeNBLocation  OPTIONAL,
	tunnelProtocol		[55] TunnelProtocol  OPTIONAL,
	pANI-Header-Info		[56] SEQUENCE OF PANI-Header-Info		OPTIONAL,
    -- information extracted from P-Access-Network-Info headers of SIP message; 
	imsVoIP 				[57] IMS-VoIP-Correlation					OPTIONAL,
	-- described in TS 24.229 §7.2A.4 [76]
	xCAPmessage			[58] OCTET STRING OPTIONAL,	
    -- The HTTP message (HTPP header and any XCAP body) of any of the target"s IMS supplementary 
	-- service setting management or manipulation XCAP messages occuring through the Ut interface
    -- defined in the 3GPP TS 24 623 [77]. 
	logicalFunctionInformation	[59] DataNodeIdentifier OPTIONAL,



	national-HI2-ASN1parameters	[256]	National-HI2-ASN1parameters	OPTIONAL
}
-- Parameters having the same tag numbers must be identical in Rel-5 and onwards modules

-- PARAMETERS FORMATS

DataNodeIdentifier ::= SEQUENCE
{
	dataNodeAddress		[1] DataNodeAddress OPTIONAL,
	logicalFunctionType	[2] LogicalFunctionType OPTIONAL,
	dataNodeName		[3] PrintableString(SIZE(7..25)) OPTIONAL,
	--Unique identifier of a Data Node within the CSP domain. Could be a name/number combination.
...
}

LogicalFunctionType ::= ENUMERATED
{
	pDNGW		(0),
	mME			(1),
	sGW			(2),
	ePDG		(3),
	hSS			(4),
...
}

PANI-Header-Info	::= SEQUENCE
{
    access-Type 		[1] OCTET STRING 		OPTIONAL,
    -- ASCII chain "3GPP-UTRAN-TDD", "3GPP-E-UTRAN-TDD",... : see TS 24.229 §7.2A.4 [76] 
    access-Class  		[2] OCTET STRING		OPTIONAL,
    -- ASCII chain "3GPP-UTRAN", "3GPP-E-UTRAN",... : see TS 24.229 §7.2A.4 [76]
    network-Provided	[3] NULL				OPTIONAL,
    -- present if provided by the network
    pANI-Location		[4] PANI-Location 		OPTIONAL,
    ...
}

PANI-Location  ::= SEQUENCE
{
    raw-Location     [1] OCTET STRING 	OPTIONAL,
    -- raw copy of the location string from the P-Access-Network-Info header
    location          [2] Location      OPTIONAL,
    ePSLocation       [3] EPSLocation   OPTIONAL,
    ...
}

PartyInformation 			::= SEQUENCE 
{
	party-Qualifier 	[0]  ENUMERATED 
	{
		gPRSorEPS-Target(3),
		...
	},
	partyIdentity 		[1] SEQUENCE 
	{
		imei					[1] OCTET STRING (SIZE (8)) OPTIONAL,
			-- See MAP format [4]

		imsi					[3] OCTET STRING (SIZE (3..8)) OPTIONAL,
			-- See MAP format [4] International Mobile 
			-- Station Identity E.212 number beginning with Mobile Country Code

		msISDN					[6] OCTET STRING (SIZE (1..9)) OPTIONAL,
			-- MSISDN of the target, encoded in the same format as the AddressString
			-- parameters defined in MAP format document TS 29.002 [4]

		e164-Format				[7] OCTET STRING    (SIZE (1 .. 25)) OPTIONAL,
			-- E164 address of the node in international format. Coded in the same format as 
			-- the calling party number  parameter of the ISUP (parameter part:[29])

		sip-uri					[8] OCTET STRING 	OPTIONAL,
			-- See [26]

		...,
		tel-uri					[9] OCTET STRING 	OPTIONAL,
			-- See [67]
        nai                    [10] OCTET STRING    OPTIONAL,
            -- NAI of the target, encoded in the same format as defined by [EPS stage 3 specs] 
		x-3GPP-Asserted-Identity [11] OCTET STRING 	OPTIONAL,	
		-- X 3GPP Asserted Identity header (3GPP TS 24 109 [79]) of the target, used in 
		-- some XCAP transactions as a complement information to SIP URI or Tel URI.
		xUI						[12] OCTET STRING 	OPTIONAL
		-- XCAP User Identifier (XUI)is a string, valid as a path element in an XCAP URI, that is 
		-- may be associated with each user served by a XCAP resource server. Defined in IETF RFC 
		-- 4825[80] as a complement information to SIP URI or Tel URI.

	},

	services-Data-Information 	[4] Services-Data-Information OPTIONAL,
		-- This parameter is used to transmit all the information concerning the
		-- complementary information associated to the basic data call
	...
}

Location	::= SEQUENCE 
{
	e164-Number         [1] OCTET STRING (SIZE (1..25)) OPTIONAL,
        -- Coded in the same format as the ISUP location number (parameter
        -- field) of the ISUP (see EN 300 356 [30]).    
	globalCellID		[2] GlobalCellID	OPTIONAL,
		--see MAP format (see [4])	
	rAI					[4] Rai		OPTIONAL,
		-- the Routeing Area Identifier in the current  SGSN is coded in accordance with the 
		-- § 10.5.5.15 of document [9] without the Routing Area Identification IEI  
		-- (only the last 6 octets are used)
	gsmLocation			[5] GSMLocation OPTIONAL,
 	umtsLocation		[6] UMTSLocation OPTIONAL,
	sAI					[7] Sai	OPTIONAL,
		-- format:	PLMN-ID	3 octets (no. 1 - 3)
		--			LAC		2 octets (no. 4 - 5)
		--			SAC		2 octets (no. 6 - 7)
		--			(according to 3GPP TS 25.413 [62])
	...,
	oldRAI				[8] Rai		OPTIONAL,
		-- the Routeing Area Identifier in the old SGSN is coded in accordance with the 
		-- § 10.5.5.15 of document [9] without the Routing Area Identification IEI 
		-- (only the last 6 octets are used).
	civicAddress		[9] CivicAddress OPTIONAL
}

       


GlobalCellID	::= OCTET STRING  (SIZE (5..7))
Rai				::= OCTET STRING (SIZE (6))
Sai				::=	OCTET STRING (SIZE (7))
       

GSMLocation 	::= CHOICE 
{
	geoCoordinates 	[1] SEQUENCE	
	{
		latitude		[1]	PrintableString (SIZE(7..10)),
							-- format : 	XDDMMSS.SS
		longitude		[2]	PrintableString (SIZE(8..11)),
							-- format : 	XDDDMMSS.SS
		mapDatum		[3]	MapDatum DEFAULT wGS84,
		...,
		azimuth			[4] INTEGER (0..359) OPTIONAL
			-- The azimuth is the bearing, relative to true north.
	},
		-- format : 	XDDDMMSS.SS
		-- 				X 			: N(orth), S(outh), E(ast), W(est)
		--				DD or DDD 	: degrees (numeric characters)
		--				MM			: minutes (numeric characters)
		--				SS.SS 		: seconds, the second part (.SS) is optionnal
		-- Example :
		--			latitude short form		N502312
		--			longitude long form		E1122312.18

	utmCoordinates	[2] SEQUENCE	
	{
		utm-East 		[1] PrintableString (SIZE(10)),		
		utm-North 		[2] PrintableString (SIZE(7)),	
			-- example	utm-East	32U0439955
			--			utm-North	5540736
		mapDatum		[3]	MapDatum DEFAULT wGS84,
		...,
		azimuth			[4] INTEGER (0..359) OPTIONAL
			-- The azimuth is the bearing, relative to true north.
 	},

	utmRefCoordinates  	[3] SEQUENCE 
	{
		utmref-string		PrintableString (SIZE(13)),
		mapDatum			MapDatum DEFAULT wGS84,
		...
	},
		-- example	32UPU91294045		

	wGS84Coordinates  	[4] OCTET STRING
		-- format is as defined in [37].
}

MapDatum ::= ENUMERATED
{	
	wGS84,
	wGS72,
	eD50, 	-- European Datum 50
	...
}

UMTSLocation ::= CHOICE {
	point					[1]	GA-Point,
	pointWithUnCertainty	[2]	GA-PointWithUnCertainty,
	polygon					[3]	GA-Polygon
}

GeographicalCoordinates ::= SEQUENCE {
	latitudeSign			ENUMERATED { north, south },
	latitude				INTEGER (0..8388607),
	longitude				INTEGER (-8388608..8388607),
	...
}

GA-Point ::= SEQUENCE {
	geographicalCoordinates		GeographicalCoordinates,
	...
}

GA-PointWithUnCertainty ::=SEQUENCE {
	geographicalCoordinates		GeographicalCoordinates,
	uncertaintyCode				INTEGER (0..127)
}

maxNrOfPoints						INTEGER ::= 15

GA-Polygon ::= SEQUENCE (SIZE (1..maxNrOfPoints)) OF
	SEQUENCE {
		geographicalCoordinates		GeographicalCoordinates,
		...
	}

SMS-report		::= SEQUENCE 
{
	sMS-Contents	[3] SEQUENCE
	{
		sms-initiator		[1] ENUMERATED 	-- party which sent the  SMS
		{
			target			(0),
			server			(1), 
			undefined-party	(2),
			...
		},
		transfer-status		[2] ENUMERATED 
		{
			succeed-transfer	(0), 		-- the transfer of the SMS message succeeds
			not-succeed-transfer(1), 
			undefined			(2),
			... 
		} OPTIONAL,
		other-message		[3] ENUMERATED 	-- in case of terminating call, indicates if
											-- the server will send other SMS
		{
			yes			(0),
			no			(1), 
			undefined	(2),
			... 
		} OPTIONAL,
		content				[4] OCTET STRING (SIZE (1 .. 270)) OPTIONAL,
									-- Encoded in the format defined for the SMS mobile 
		... 
	}	
}

EPSCorrelationNumber ::= OCTET STRING 
       -- In case of PS interception, the size will be in the range (8..20)
CorrelationValues ::= CHOICE {
		
		iri-to-CC 	[0]		IRI-to-CC-Correlation, -- correlates IRI to Content(s)
		iri-to-iri	[1]		IRI-to-IRI-Correlation, -- correlates IRI to IRI 
		both-IRI-CC	[2]		SEQUENCE { -- correlates IRI to IRI and IRI to Content(s)
								iri-CC	[0]	IRI-to-CC-Correlation,
								iri-IRI	[1]	IRI-to-IRI-Correlation}
}
 
 
IMS-VoIP-Correlation ::= SET OF SEQUENCE {
			ims-iri		[0]		IRI-to-IRI-Correlation,
			ims-cc		[1]		IRI-to-CC-Correlation 		OPTIONAL
}

IRI-to-CC-Correlation ::= SEQUENCE { -- correlates IRI to Content
			cc 		[0] SET OF 	OCTET STRING,-- correlates IRI to multiple CCs
			iri 	[1] 		OCTET STRING OPTIONAL 
									-- correlates IRI to CC with signaling
}
IRI-to-IRI-Correlation ::= OCTET STRING -- correlates IRI to IRI


EPSEvent ::= ENUMERATED 
{
	pDPContextActivation 					(1),
	startOfInterceptionWithPDPContextActive	(2),
	pDPContextDeactivation					(4),
	gPRSAttach 								(5),
	gPRSDetach 								(6),
	locationInfoUpdate 						(10),
	sMS 									(11),
	pDPContextModification					(13),
	servingSystem							(14),
	... ,
	startOfInterceptionWithMSAttached		(15),
    e-UTRANAttach							(16),
    e-UTRANDetach                           (17),
    bearerActivation                        (18),
    startOfInterceptionWithActiveBearer     (19),
    bearerModification                      (20),
    bearerDeactivation                      (21),
    uERequestedBearerResourceModification   (22),
    uERequestedPDNConnectivity              (23),
    uERequestedPDNDisconnection             (24),
    trackingAreaEpsLocationUpdate           (25),
    servingEvolvedPacketSystem              (26),
    pMIPAttachTunnelActivation              (27),
    pMIPDetachTunnelDeactivation            (28),
    startOfInterceptWithActivePMIPTunnel    (29),
    pMIPPdnGwInitiatedPdnDisconnection      (30),
    mIPRegistrationTunnelActivation         (31),
    mIPDeregistrationTunnelDeactivation     (32),
    startOfInterceptWithActiveMIPTunnel     (33),
    dSMIPRegistrationTunnelActivation       (34),
    dSMIPDeregistrationTunnelDeactivation   (35),
    startOfInterceptWithActiveDsmipTunnel   (36),
    dSMipHaSwitch                           (37),
    pMIPResourceAllocationDeactivation      (38),
    mIPResourceAllocationDeactivation       (39),
    pMIPsessionModification                 (40),
    startOfInterceptWithEUTRANAttachedUE    (41),
    dSMIPSessionModification                (42),
	packetDataHeaderInformation				(43)

}
-- see [19]

IMSevent ::= ENUMERATED 
{
	unfilteredSIPmessage (1),
		-- This value indicates to LEMF that the whole SIP message is sent , i.e. without filtering
        -- CC; location information is removed by the DF2/MF if not required to be sent.

	...,
	sIPheaderOnly (2),
		-- If warrant requires only IRI then specific content in a 'sIPMessage'
		-- (e.g. 'Message', etc.) has been deleted before sending it to LEMF.

    decryptionKeysAvailable (3),
		-- This value indicates to LEMF that the IRI carries CC decryption keys for the session
        -- under interception. 

    startOfInterceptionForIMSEstablishedSession (4),
        -- This value indicates to LEMF that the IRI carries information related to
        -- interception started on an already established IMS session. 
	xCAPRequest (5),
		-- This value indicates to LEMF that the XCAP request is sent.
	xCAPResponse (6)
		-- This value indicates to LEMF that the XCAP response is sent.

}

Services-Data-Information ::= SEQUENCE
{
	gPRS-parameters [1] GPRS-parameters OPTIONAL,
	...
}

GPRS-parameters ::= SEQUENCE 
{
	pDP-address-allocated-to-the-target 	[1] DataNodeAddress OPTIONAL,
	aPN 					[2] OCTET STRING (SIZE(1..100)) OPTIONAL,
	    -- The Access Point Name (APN) is coded in accordance with
		-- 3GPP TS 24.008 [9] without the APN IEI (only the last 100 octets are used).
		-- Octets are coded according to 3GPP TS 23.003 [25].

	pDP-type 				[3] OCTET STRING (SIZE(2)) OPTIONAL, 
   -- Include either Octets 3 and 4 of the Packet Data Protocol Address information element
    -- of 3GPP TS 24.008 [9] or Octets 4 and 5 of the End User Address IE of 3GPP TS 29.060 [17].
	-- when PDP-type is IPv4 or IPv6, the IP address is carried by parameter
	-- pDP-address-allocated-to-the-target
	-- when PDP-type is IPv4v6, the additional IP address is carried by parameter
	-- additionalIPaddress
	...,
	nSAPI					[4] OCTET STRING (SIZE (1)) OPTIONAL,
    -- Include either Octet 2 of the NSAPI IE of 3GPP TS 24.008 [9] 
    -- or Octet 2 of the NSAPI IE of 3GPP TS 29.060 [17].
	additionalIPaddress		[5] DataNodeAddress OPTIONAL
}

GPRSOperationErrorCode ::= OCTET STRING
-- The parameter shall carry the GMM cause value or the SM cause value, as defined in the
-- standard [9], without the IEI.


LDIevent ::= ENUMERATED 
{
	targetEntersIA 			(1),
	targetLeavesIA			(2),
	...
}

UmtsQos ::= CHOICE
{
	qosMobileRadio [1] OCTET STRING,
		-- The qosMobileRadio parameter shall be coded in accordance with the § 10.5.6.5 of
		-- document [9] without the Quality of service IEI and Length of 
		-- quality of service IE (. That is, first 
		-- two octets carrying 'Quality of service IEI' and 'Length of quality of service
 		-- IE' shall be excluded). 
	qosGn [2] OCTET STRING
		-- qosGn parameter shall be coded in accordance with § 7.7.34 of document [17]
} 


EPS-GTPV2-SpecificParameters ::= SEQUENCE
{
    pDNAddressAllocation                 [1]   OCTET STRING                       OPTIONAL,
    aPN                                  [2]   OCTET STRING (SIZE (1..100))       OPTIONAL,
    protConfigOptions                    [3]   ProtConfigOptions                  OPTIONAL,
    attachType                           [4]   OCTET STRING (SIZE (1))            OPTIONAL,
    -- coded according to TS 24.301 [47]
    ePSBearerIdentity                    [5]   OCTET STRING                       OPTIONAL,
    detachType                           [6]   OCTET STRING (SIZE (1))            OPTIONAL,
    -- coded according to TS 24.301 [47], includes switch off indicator
    rATType                              [7]   OCTET STRING (SIZE (1))            OPTIONAL,
    failedBearerActivationReason         [8]   OCTET STRING (SIZE (1))            OPTIONAL,
    ePSBearerQoS                         [9]   OCTET STRING                       OPTIONAL,
    bearerActivationType                 [10]  TypeOfBearer                       OPTIONAL,
    aPN-AMBR                             [11]  OCTET STRING                       OPTIONAL,
    -- Only octets 5 onwards of AMBR IE from 3GPP TS 29.274 [46] shall be included.
    procedureTransactionId               [12]  OCTET STRING                       OPTIONAL,
    linkedEPSBearerId                    [13]  OCTET STRING                       OPTIONAL,
    --The Linked EPS Bearer Identity shall be included and coded according to 3GPP TS 29.274 [46].
    tFT                                  [14]  OCTET STRING                       OPTIONAL,
    -- Only octets 3 onwards of TFT IE from 3GPP TS 24.008 [9] shall be included.
    handoverIndication                   [15]  NULL                               OPTIONAL,
    failedBearerModReason                [16]  OCTET STRING (SIZE (1))            OPTIONAL,
    trafficAggregateDescription          [17]  OCTET STRING                       OPTIONAL,
    failedTAUReason                      [18]  OCTET STRING (SIZE (1))            OPTIONAL,
    -- coded according to TS 24.301 [47]
    failedEUTRANAttachReason             [19]  OCTET STRING (SIZE (1))            OPTIONAL,
    -- coded according to TS 24.301 [47]      
    servingMMEaddress                    [20]  OCTET STRING                       OPTIONAL,
	-- Contains the data fields from the Diameter Origin-Host and Origin-Realm AVPs
	-- as received in the HSS from the MME according to the TS 29.272 [59].
	-- Only the data fields from the Diameter AVPs are provided concatenated 
	-- with a semicolon to populate this field.
    bearerDeactivationType               [21]  TypeOfBearer                       OPTIONAL,
    bearerDeactivationCause              [22]  OCTET STRING (SIZE (1))            OPTIONAL,
    ePSlocationOfTheTarget               [23]  EPSLocation                        OPTIONAL,
      -- the use of ePSLocationOfTheTarget is mutually exclusive with the use of locationOfTheTarget
      -- ePSlocationOfTheTarget allows using the coding of the parameter according to SAE stage 3.
    ...,
	pDNType                              [24]   OCTET STRING (SIZE (1))           OPTIONAL,
    -- coded according to TS 24.301 [47]

    requestType                          [25]  OCTET STRING (SIZE (1))            OPTIONAL,
      -- coded according to TS 24.301 [47]
    uEReqPDNConnFailReason               [26]  OCTET STRING (SIZE (1))            OPTIONAL,
      -- coded according to TS 24.301 [47] 
	extendedHandoverIndication			 [27]  OCTET STRING (SIZE (1)) 			  OPTIONAL,
	-- This parameter with value 1 indicates handover based on the flags in the TS 29.274 [46].
	-- Otherwise set to the value 0. 
	-- The use of extendedHandoverIndication and handoverIndication parameters is 
	-- mutually exclusive and depends on the actual ASN.1 encoding method. 

    uLITimestamp                         [28]  OCTET STRING (SIZE (8))            OPTIONAL

    }  

   -- All the parameters within EPS-GTPV2-SpecificParameters are coded as the corresponding IEs 
   -- without the octets containing type and length. Unless differently stated, they are coded
   -- according to 3GPP TS 29.274 [46]; in this case the octet containing the instance
   -- shall also be not included.



TypeOfBearer ::= ENUMERATED
{
    defaultBearer          (1),
    dedicatedBearer        (2),
    ...
}





EPSLocation	::= SEQUENCE 
{
   
	userLocationInfo    [1] OCTET STRING (SIZE (1..39)) OPTIONAL,
        -- coded according to 3GPP TS 29.274 [46]; the type IE is not included 
	gsmLocation			[2] GSMLocation OPTIONAL,
 	umtsLocation		[3] UMTSLocation OPTIONAL,
	olduserLocationInfo	[4] OCTET STRING (SIZE (1..39))	OPTIONAL,
        -- coded in the same way as userLocationInfo
	lastVisitedTAI	    [5] OCTET STRING (SIZE (1..5))	OPTIONAL,
        -- the Tracking Area Identity is coded in accordance with the TAI field in 3GPP TS 29.274
        -- [46].
	tAIlist			    [6] OCTET STRING (SIZE (7..97))	OPTIONAL,
       -- the TAI List is coded acording to 3GPP TS 24.301 [47], without the TAI list IEI
    ...,
	threeGPP2Bsid		[7] OCTET STRING (SIZE (1..12)) OPTIONAL,
		-- contains only the payload from the 3GPP2-BSID AVP described in the 3GPP TS 29.212 [56].
	civicAddress		[8] CivicAddress OPTIONAL


}

ProtConfigOptions ::= SEQUENCE

{
    ueToNetwork                           [1]  OCTET STRING (SIZE(1..251))        OPTIONAL,
    -- This shall be coded with octet 3 onwards of the Protocol Configuration Options IE in
    -- accordance with 3GPP TS 24.008 [9].  
 	networkToUe                           [2]  OCTET STRING (SIZE(1..251))        OPTIONAL,
    -- This shall be coded with octet 3 onwards of the Protocol Configuration Options IE in
    -- accordance with 3GPP TS 24.008 [9].    
...
}



EPS-PMIP-SpecificParameters ::= SEQUENCE
{
    lifetime                              [1]  INTEGER (0..65535)                 OPTIONAL,
    accessTechnologyType                  [2]  OCTET STRING (SIZE (4))            OPTIONAL,
    aPN                                   [3]  OCTET STRING (SIZE (1..100))       OPTIONAL,
    iPv6HomeNetworkPrefix                 [4]  OCTET STRING (SIZE (20))           OPTIONAL,
    protConfigurationOption               [5]  OCTET STRING                       OPTIONAL,
    handoverIndication                    [6]  OCTET STRING (SIZE (4))            OPTIONAL,
    status                                [7]  INTEGER (0..255)                   OPTIONAL,
    revocationTrigger                     [8]  INTEGER (0..255)                   OPTIONAL, 
    iPv4HomeAddress                       [9]  OCTET STRING (SIZE (4))            OPTIONAL,
    iPv6careOfAddress                     [10] OCTET STRING                       OPTIONAL,
    iPv4careOfAddress                     [11] OCTET STRING                       OPTIONAL,
    ...,
    servingNetwork                        [12] OCTET STRING (SIZE (3))            OPTIONAL,
    dHCPv4AddressAllocationInd            [13] OCTET STRING (SIZE (1))            OPTIONAL,
    ePSlocationOfTheTarget                [14] EPSLocation                        OPTIONAL
    
    -- parameters coded according to 3GPP TS 29.275 [48] and RFCs specifically
	-- referenced in it.
}


EPS-DSMIP-SpecificParameters ::= SEQUENCE
{
    lifetime                              [1]   INTEGER (0..65535)                OPTIONAL,
    requestedIPv6HomePrefix               [2]   OCTET STRING (SIZE (25))          OPTIONAL,
    -- coded according to RFC 5026
    homeAddress                           [3]   OCTET STRING (SIZE (8))           OPTIONAL,
    iPv4careOfAddress                     [4]   OCTET STRING (SIZE (8))           OPTIONAL,
    iPv6careOfAddress                     [5]   OCTET STRING (SIZE(16))           OPTIONAL,
    aPN                                   [6]   OCTET STRING (SIZE (1..100))      OPTIONAL,
    status                                [7]   INTEGER (0..255)                  OPTIONAL,
    hSS-AAA-address                       [8]   OCTET STRING                      OPTIONAL,
    targetPDN-GW-Address                  [9]   OCTET STRING                      OPTIONAL,
    ...
    -- parameters coded according to 3GPP TS 24.303 [49] and RFCs specifically
	-- referenced in it.
}


EPS-MIP-SpecificParameters ::= SEQUENCE
{
    lifetime                              [1]   INTEGER (0.. 65535)               OPTIONAL,
    homeAddress                           [2]   OCTET STRING (SIZE (4))           OPTIONAL,
    careOfAddress                         [3]   OCTET STRING (SIZE (4))           OPTIONAL,
    homeAgentAddress                      [4]   OCTET STRING (SIZE (4))           OPTIONAL,
    code                                  [5]   INTEGER (0..255)                  OPTIONAL,
    foreignDomainAddress                  [7]   OCTET STRING (SIZE (4))           OPTIONAL,
    ...
    -- parameters coded according to 3GPP TS 29.279 [63] and RFCs specifically
	-- referenced in it.
}


MediaDecryption-info ::= SEQUENCE OF CCKeyInfo
		-- One or more key can be available for decryption, one for each media streams of the
        -- intercepted session.

CCKeyInfo ::= SEQUENCE
{
	cCCSID	 [1]	OCTET STRING,	
		-- the parameter uniquely mapping the key to the encrypted stream. 
	cCDecKey [2]	OCTET STRING,
	cCSalt   [3]    OCTET STRING OPTIONAL,
        -- The field reports the value from the CS_ID field in the ticket exchange headers as
        -- defined in IETF RFC 6043 [61].
	...
}

MediaSecFailureIndication  ::= ENUMERATED
{
    genericFailure  (0),
    ...
}
 

PacketDataHeaderInformation ::= CHOICE
{

	packetDataHeader		[1]	PacketDataHeader,
	packetDataHeaderSummary	[2]	PacketDataHeaderSummary,
...
}

PacketDataHeader ::= CHOICE
{

	packetDataHeaderMapped	[1]	PacketDataHeaderMapped,
	packetDataHeaderCopy	[2]	PacketDataHeaderCopy,
...
}

PacketDataHeaderMapped ::= SEQUENCE 
{
	sourceIPAddress			[1] IPAddress,
	sourcePortNumber		[2] INTEGER (0..65535) OPTIONAL,	
	destinationIPAddress	[3] IPAddress,
	destinationPortNumber	[4] INTEGER (0..65535) OPTIONAL,
	transportProtocol		[5] INTEGER,
	-- For IPv4, report the 'Protocol' field and for IPv6 report 'Next Header' field.
	-- Assigned Internet Protocol Numbers can be found at 
	-- http://www.iana.org/assignments/protocol-numbers/protocol-numbers.xml
	packetsize				[6] INTEGER OPTIONAL,
	flowLabel				[7] INTEGER OPTIONAL,
	packetCount				[8] INTEGER OPTIONAL,
	direction				[9] TPDU-direction,
...
} 


TPDU-direction ::= ENUMERATED
{
	from-target 	(1),
	to-target 		(2),
	unknown 		(3)
}


PacketDataHeaderCopy ::= SEQUENCE 
{
	direction				[1] TPDU-direction,
	headerCopy				[2] OCTET STRING,	-- includes a copy of the packet header at the IP 
				-- network layer and above including extension headers, but excluding contents.
...
} 


PacketDataHeaderSummary ::= SEQUENCE OF PacketFlowSummary

PacketFlowSummary ::= SEQUENCE
{

	sourceIPAddress			[1] IPAddress,
	sourcePortNumber		[2] INTEGER (0..65535) OPTIONAL,	
	destinationIPAddress	[3] IPAddress,
	destinationPortNumber	[4] INTEGER (0..65535) OPTIONAL,
	transportProtocol		[5] INTEGER,
	-- For IPv4, report the 'Protocol' field and for IPv6 report 'Next Header' field.
	-- Assigned Internet Protocol Numbers can be found at 
	-- http://www.iana.org/assignments/protocol-numbers/protocol-numbers.xml
	flowLabel				[6] INTEGER OPTIONAL,
	summaryPeriod			[7] ReportInterval,
	packetCount				[8] INTEGER,
	sumOfPacketSizes		[9] INTEGER,
	packetDataSummaryReason	[10] ReportReason,
...
} 


ReportReason ::= ENUMERATED
{
	timerExpired			(0),	
	countThresholdHit		(1),
	pDPComtextDeactivated   (2),
	pDPContextModification	(3),
	otherOrUnknown			(4),
	...
} 

ReportInterval ::= SEQUENCE
{
	firstPacketTimeStamp	[0] TimeStamp,
	lastPacketTimeStamp		[1] TimeStamp,
	...
} 


TunnelProtocol ::= CHOICE 
{

  rfc2868ValueField [0] OCTET STRING, -- coded to indicate the type of tunnel established between 
  -- the HeNB and the SeGW as specified in TS 33.320.  The actual coding is provided in 3 octets 
  -- with the Value field of the Tunnel Type RADIUS attribute as specified in IETF RFC 2868. 
  -- This corresponds to the outer layer tunnel between the HeNB and the SeGW as viewed by the 
  -- SeGW
  nativeIPSec       [1] NULL, -- if native IPSec is required by TS 33.320 between HeNB and SeGW
...
} 
HeNBLocation ::= EPSLocation


END -- OF EpsHI2Operations




-- Source: Umts-HI3-PS,rel12.txt
-- ETSI TS 133 108 V12.11.0 (2016-01)
-- Annex B.4	HI3 PS

Umts-HI3-PS {itu-t(0) identified-organization(4) etsi(0) securityDomain(2) lawfulintercept(2) threeGPP(4) hi3(2) r7(7) version-0(0)}
 
DEFINITIONS IMPLICIT TAGS ::=

BEGIN

IMPORTS
		
GPRSCorrelationNumber
	FROM UmtsHI2Operations
	{itu-t(0) identified-organization(4) etsi(0) securityDomain(2) lawfulintercept(2) threeGPP(4) 	hi2(1) r7(7) version-2(2)}    -- Imported from TS 33.108v7.2.0

LawfulInterceptionIdentifier,
	
TimeStamp
	FROM HI2Operations 
	{itu-t(0) identified-organization(4) etsi(0) securityDomain(2) lawfulIntercept(2) hi2(1) 	version9(9)};  -- from ETSI HI2Operations TS 101 671v2.13.1

-- Object Identifier Definitions

-- Security DomainId
lawfulInterceptDomainId OBJECT IDENTIFIER ::= {itu-t(0) identified-organization(4) etsi(0)
securityDomain(2) lawfulIntercept(2)}

-- Security Subdomains
threeGPPSUBDomainId OBJECT IDENTIFIER ::= {lawfulInterceptDomainId threeGPP(4)}
hi3DomainId OBJECT IDENTIFIER  ::= {threeGPPSUBDomainId hi3(2) r7(7) version-0(0)}

CC-PDU	::= SEQUENCE 
{
 	uLIC-header		[1] ULIC-header, 
	payload			[2] OCTET STRING
}

ULIC-header ::= SEQUENCE 
{
	hi3DomainId				[0]	OBJECT IDENTIFIER,  -- 3GPP HI3 Domain
	version					[1]	Version,
	lIID					[2] LawfulInterceptionIdentifier OPTIONAL,
	correlation-Number		[3]	GPRSCorrelationNumber,
	timeStamp				[4]	TimeStamp OPTIONAL,
	sequence-number			[5]	INTEGER (0..65535),
	t-PDU-direction			[6] TPDU-direction,
	...,
	national-HI3-ASN1parameters		[7] National-HI3-ASN1parameters OPTIONAL,
	--  encoded per national requirements
	ice-type				[8] ICE-type OPTIONAL
		-- The ICE-type indicates the applicable Intercepting Control Element(see ref [19]) in which
		-- the T-PDU is intercepted.
}

Version ::= ENUMERATED
{
	version1(1),
	...,
	version3(3) ,
		-- versions 4-7 were omitted to align with UmtsHI2Operations.
	lastVersion(8)
		-- Mandatory parameter "version" (tag 1) was always redundant in 33.108, because 
		-- the object identifier "hi3DomainId" was introduced into "ULIC-headerV in the initial
		-- version of 33.108v5.0.0 In order to keep backward compatibility, even when the
		-- version of the "hi3DomainId" parameter will be incremented it is recommended to
		-- always send to LEMF the same: enumeration value "lastVersion(8)".
}

TPDU-direction ::= ENUMERATED
{
	from-target 	(1),
	to-target 		(2),
	unknown 		(3)
}

National-HI3-ASN1parameters	::= SEQUENCE
{
	countryCode		[1] PrintableString (SIZE (2)),
		-- Country Code according to ISO 3166-1 [39],
		-- the country to which the parameters inserted after the extension marker apply
	...
		-- In case a given country wants to use additional national parameters according to its law,
		-- these national parameters should be defined using the ASN.1 syntax and added after the
		-- extension marker (...).
		-- It is recommended that "version parameter" and "vendor identification parameter" are
		-- included in the national parameters definition. Vendor identifications can be
		-- retrieved from IANA web site. It is recommended to avoid
		-- using tags from 240 to 255 in a formal type definition.
}

ICE-type ::= ENUMERATED
{
	sgsn			(1),
	ggsn			(2),
	...
}

END-- OF Umts-HI3-PS




-- Source: Eps-HI3-PS,rel12.txt
-- ETSI TS 133 108 V12.11.0 (2016-01)
-- Annex B.10	HI3 EPS

Eps-HI3-PS {itu-t(0) identified-organization(4) etsi(0) securityDomain(2) lawfulintercept(2) threeGPP(4) hi3eps(9)  r12(12) version-0(0)}
 
DEFINITIONS IMPLICIT TAGS ::=

BEGIN

IMPORTS
		
EPSCorrelationNumber
	FROM EpsHI2Operations
	{itu-t(0) identified-organization(4) etsi(0) securityDomain(2) lawfulintercept(2) threeGPP(4) 	hi2eps(8) r12(12) version-55(55)}    -- Imported from TS 33.108 v.12.5.0

LawfulInterceptionIdentifier,
	
TimeStamp
	FROM HI2Operations 
	{itu-t(0) identified-organization(4) etsi(0) securityDomain(2) lawfulIntercept(2) hi2(1) 	version18(18)};  -- from ETSI HI2Operations TS 101 671 v3.12.1

-- Object Identifier Definitions

-- Security DomainId
lawfulInterceptDomainId OBJECT IDENTIFIER ::= {itu-t(0) identified-organization(4) etsi(0)
securityDomain(2) lawfulIntercept(2)}

-- Security Subdomains
threeGPPSUBDomainId OBJECT IDENTIFIER ::= {lawfulInterceptDomainId threeGPP(4)}
hi3DomainId OBJECT IDENTIFIER  ::= {threeGPPSUBDomainId hi3eps(9) r12(12) version-0(0)}

CC-PDU	::= SEQUENCE 
{
 	uLIC-header		[1] ULIC-header, 
	payload			[2] OCTET STRING
}

ULIC-header ::= SEQUENCE 
{
	hi3DomainId				[0]	OBJECT IDENTIFIER,  -- 3GPP HI3 Domain
	lIID					[2] LawfulInterceptionIdentifier OPTIONAL,
	correlation-Number		[3]	EPSCorrelationNumber,
	timeStamp				[4]	TimeStamp OPTIONAL,
	sequence-number			[5]	INTEGER (0..65535),
	t-PDU-direction			[6] TPDU-direction,
	...,
	national-HI3-ASN1parameters		[7] National-HI3-ASN1parameters OPTIONAL,
	--  encoded per national requirements
	ice-type				[8] ICE-type OPTIONAL
		-- The ICE-type indicates the applicable Intercepting Control Element(see ref [19]) in which
		-- the T-PDU is intercepted.
}


TPDU-direction ::= ENUMERATED
{
	from-target 	(1),
	to-target 		(2),
	unknown 		(3)
}

National-HI3-ASN1parameters	::= SEQUENCE
{
	countryCode		[1] PrintableString (SIZE (2)),
		-- Country Code according to ISO 3166-1 [39],
		-- the country to which the parameters inserted after the extension marker apply
	...
		-- In case a given country wants to use additional national parameters according to its law,
		-- these national parameters should be defined using the ASN.1 syntax and added after the
		-- extension marker (...).
		-- It is recommended that "version parameter" and "vendor identification parameter" are
		-- included in the national parameters definition. Vendor identifications can be
		-- retrieved from IANA web site. It is recommended to avoid
		-- using tags from 240 to 255 in a formal type definition.
}

ICE-type ::= ENUMERATED
{
	sgsn			(1),
	ggsn			(2),
	...,
    s-GW            (3),
    pDN-GW          (4),
    colocated-SAE-GWs (5) ,
    ePDG            (6)
}

END-- OF Eps-HI3-PS




-- Source: ThreeGPP-HI1NotificationOperations,rel12.txt
-- ETSI TS 133 108 V12.11.0 (2016-01)
-- Annex M.2	LI Management notification operation HI1

ThreeGPP-HI1NotificationOperations
{itu-t(0) identified-organization(4) etsi(0) securityDomain(2) lawfulIntercept(2) threeGPP(4) hi1(0) notificationOperations(1) r12(12)version-2 (2)}

DEFINITIONS IMPLICIT TAGS ::=

BEGIN

IMPORTS
	OPERATION,
	ERROR
		FROM Remote-Operations-Information-Objects
		{joint-iso-itu-t(2) remote-operations(4) informationObjects(5) version1(0)}
	
		LawfulInterceptionIdentifier,
		TimeStamp,
		CommunicationIdentifier,
		Network-Identifier,
				CalledPartyNumber,
		IPAddress
		
		FROM HI2Operations
			{itu-t(0) identified-organization(4) etsi(0) securityDomain(2)
 				  lawfulIntercept(2) hi2(1) version18(18)}; -- Imported from TS 101 671v3.12.1




-- =============================
-- Object Identifier Definitions
-- =============================

-- LawfulIntercept DomainId
lawfulInterceptDomainId OBJECT IDENTIFIER ::= {itu-t(0) identified-organization(4) etsi(0) securityDomain(2) lawfulIntercept(2)}
-- Security Subdomains
threeGPPSUBDomainId OBJECT IDENTIFIER ::= {lawfulInterceptDomainId threeGPP(4)}
-- hi1 Domain
threeGPP-hi1NotificationOperationsId OBJECT IDENTIFIER ::= {threeGPPSUBDomainId hi1(0) notificationOperations(1)}
threeGPP-hi1OperationId OBJECT IDENTIFIER ::= {threeGPP-hi1NotificationOperationsId r12(12)  version2 (2)}

threeGPP-sending-of-HI1-Notification OPERATION ::=
{
	ARGUMENT	ThreeGPP-HI1-Operation
	ERRORS		{Error-ThreeGPP-HI1Notifications}
	CODE		global:{threeGPP-hi1NotificationOperationsId version0(0)}
}
-- Class 2 operation. The timer should be set to a value between 3s and 240s.
-- The timer default value is 60s.
-- NOTE: The value for this timer is to be set on the equipment waiting for the returned message;
-- its value should be agreed between the NWO/AP/SvP and the LEA, depending on their equipment
-- properties.

other-failure-causes	ERROR ::= {CODE local:0}
missing-parameter		ERROR ::= {CODE local:1}
unknown-parameter		ERROR ::= {CODE local:2}
erroneous-parameter		ERROR ::= {CODE local:3}

Error-ThreeGPP-HI1Notifications ERROR ::=
{
	other-failure-causes |
	missing-parameter |
	unknown-parameter |
	erroneous-parameter
}


ThreeGPP-HI1-Operation ::= CHOICE
{
	liActivated					[1] Notification,
	liDeactivated				[2] Notification,
	liModified					[3] Notification,
	alarms-indicator			[4] Alarm-Indicator,
	threeGPP-National-HI1-ASN1parameters	[5] ThreeGPP-National-HI1-ASN1parameters,
...}

-- ==================
-- PARAMETERS FORMATS
-- ==================

Notification ::= SEQUENCE
{
	domainID						[0] OBJECT IDENTIFIER (threeGPP-hi1OperationId) OPTIONAL,
		-- Once using FTP delivery mechanism
	lawfulInterceptionIdentifier	[1] LawfulInterceptionIdentifier,
	-- This identifier is the LIID identity provided with the lawful authorization for each
	-- target.
	communicationIdentifier			[2] CommunicationIdentifier OPTIONAL,
		-- Only the NO/AP/SP Identifier is provided (the one provided with the Lawful
		-- authorization) in CS domain.		
	timeStamp						[3] TimeStamp,
	-- date and time of the report.
	threeGPP-National-HI1-ASN1parameters		[5] ThreeGPP-National-HI1-ASN1parameters OPTIONAL,
	target-Information				[6] Target-Information OPTIONAL,
	network-Identifier				[7] Network-Identifier OPTIONAL,
		-- Same definition of annexes B3, B8, B9, B.11.1. It is recommended to use the same value 
		-- than those decided by the CSP and the LEA as the NWO/PA/SvPIdentifier of 
		-- communicationIdentifier used in CS domain.   
	broadcastStatus					[8] BroadcastStatus OPTIONAL,
...}


Alarm-Indicator ::= SEQUENCE
{
	domainID						[0] OBJECT IDENTIFIER (threeGPP-hi1OperationId) OPTIONAL,
		-- Once using FTP delivery mechanism
	communicationIdentifier			[1] CommunicationIdentifier OPTIONAL,
		-- Only the NO/AP/SP Identifier is provided (the one provided with the
		-- Lawful authorization)
	timeStamp						[2] TimeStamp,
		-- date and time of the report.
	alarm-information				[3] OCTET STRING (SIZE (1..25)),
		-- Provides information about alarms (free format).
	lawfulInterceptionIdentifier	[4] LawfulInterceptionIdentifier OPTIONAL,
		-- This identifier is the LIID identity provided with the lawful authorization
		-- for each target in according to national law
	threeGPP-National-HI1-ASN1parameters		[5] ThreeGPP-National-HI1-ASN1parameters OPTIONAL,
	target-Information				[6] Target-Information OPTIONAL,
	network-Identifier				[7] Network-Identifier OPTIONAL,
	-- the NO/AP/SP Identifier,
		-- Same definition as annexes B3, B8, B9, B.11.1
	network-Element-Information		[8] OCTET STRING (SIZE (1..256)) OPTIONAL,
		-- This identifier may be a network element identifier such an IP address with its IP value,
		-- that may not work properly. To be defined between the CSP and the LEA.
...}

ThreeGPP-National-HI1-ASN1parameters ::= SEQUENCE
{
	domainID		[0] OBJECT IDENTIFIER (threeGPP-hi1OperationId) OPTIONAL,
		-- Once using FTP delivery mechanism.
	countryCode		[1] PrintableString (SIZE (2)),
		-- Country Code according to ISO 3166-1 [39],
		-- the country to which the parameters inserted after the extension marker apply.
		-- In case a given country wants to use additional national parameters according to its law,
		-- these national parameters should be defined using the ASN.1 syntax and added after the
		-- extension marker (...).
		-- It is recommended that "version parameter" and "vendor identification parameter" are
		-- included in the national parameters definition. Vendor identifications can be
		-- retrieved from IANA web site. Besides, it is recommended to avoid
		-- using tags from 240 to 255 in a formal type definition.
...}

Target-Information ::= SEQUENCE
{
	communicationIdentifier	[0] CommunicationIdentifier OPTIONAL,
		-- Only the NO/AP/SP Identifier is provided (the one provided with the
		-- Lawful authorization)
	network-Identifier	[1] Network-Identifier OPTIONAL,
		-- the NO/PA/SPIdentifier,
		-- Same definition of annexes B3, B8, B9, B.11.1
	broadcastArea		[2] OCTET STRING (SIZE (1..256)) OPTIONAL,
		-- A Broadcast Area is used to select the group of NEs (network elements) which an 
		-- interception applies to. This group may be built on the basis of network type, technology 
		-- type or geographic details to fit national regulation and jurisdiction. The pre-defined 
		-- values may be decided by the CSP and the LEA to determinate the specific part of the 
		-- network or plateform on which the target identity(ies) has to be activated or 
		-- desactivated. 
	targetType			[3] TargetType OPTIONAL,
	deliveryInformation	[4] DeliveryInformation OPTIONAL,
	liActivatedTime		[5] TimeStamp OPTIONAL,
	liDeactivatedTime	[6] TimeStamp OPTIONAL,
	liModificationTime	[7] TimeStamp OPTIONAL,
	interceptionType	[8] InterceptionType OPTIONAL,
...,
	liSetUpTime        [9] TimeStamp OPTIONAL
	-- date and time when the warrant is entered into the ADMF
}


TargetType ::= ENUMERATED
{
	mSISDN(0),
	iMSI(1),
	iMEI(2),
	e164-Format(3),
	nAI(4),
	sip-URI(5),
	tel-URI(6),
	iMPU (7),
	iMPI (8),
...
}

DeliveryInformation ::= SEQUENCE
{
	hi2DeliveryNumber 		[0] CalledPartyNumber OPTIONAL,
	-- Circuit switch IRI delivery E164 number 
	hi3DeliveryNumber 		[1] CalledPartyNumber OPTIONAL,
	-- Circuit switch voice content delivery E164 number 
	hi2DeliveryIpAddress 	[2] IPAddress OPTIONAL,
	-- HI2 address of the LEMF.
	hi3DeliveryIpAddress	[3] IPAddress OPTIONAL,
	-- HI3 address of the LEMF.
...}

InterceptionType ::= ENUMERATED
{
      voiceIriCc(0),
      voiceIriOnly(1),
      dataIriCc(2),
      dataIriOnly(3),
      voiceAndDataIriCc(4),
      voiceAndDataIriOnly(5),
...}


BroadcastStatus ::= ENUMERATED
{
	succesfull(0),
	-- Example of usage: following a broadcasted command at least the target list of one node with a LI function has 
	-- been modified or confirm to include the target id requested by the LEA.
	unsuccesfull(1),
	-- case of usage: such information could be provided to the LEMF following the impossibility to get a positive confirmation from at least one node with an LI function on the broadcasted command made by the operator"s mediation or the management of mediation.
...}


END -- end of ThreeGPP-HI1NotificationOperations




-- Source: ETSI TS 101 909-20-1 V1.1.2 (2005-10)
-- Annex A
TS101909201 {itu-t (0) identified-organization (4) etsi (0) ts101909 (1909) part20 (20) subpart1(1) interceptVersion (0)}
DEFINITIONS AUTOMATIC TAGS ::=
BEGIN
IMPORTS
	CdcPdu	FROM
		PCESP {iso(1) identified-organization(3) dod(6) internet(1) private(4)
		enterprise(1) cable-Television-Laboratories-Inc(4491) clabProject(2)
		clabProjPacketCable(2) pktcLawfulIntercept(5) pcesp(1) version-4(4)};
TARGETACTIVITYMONITOR-1 ::= SEQUENCE
{
    version                      INTEGER DEFAULT 1,         -- header, version -
    lIInstanceid                 LIIDType,                  -- header, who -
    timestamp                    UTCTime,                   -- header, when -
    targetLocation               LocationType,              -- header, where -
    direction                    DirectionType,
    iRITransaction               IRITransactionType DEFAULT iRIreport,
    iRITransactionNumber         INTEGER,
    userSignal                   UserSignalType,            -- Either copy or interpreted signalling
    cryptoCheckSum               BIT STRING             OPTIONAL
}
TTRAFFIC ::= SEQUENCE
{
	    version                   INTEGER DEFAULT 1,      -- header, version -
        lIInstanceid              LIIDType,
        iRITransactionNumber      INTEGER,
        trafficPacket             BIT STRING,
        cryptoChecksum            BIT STRING    OPTIONAL
}
CTTRAFFIC ::= SEQUENCE
{
	    version                   INTEGER DEFAULT 1,      -- header, version -
        lIInstanceid              LIIDType,
        correspondentCount        INTEGER,
        iRITransactionNumber      INTEGER,
        trafficPacket             BIT STRING,
        cryptoChecksum            BIT STRING    OPTIONAL
}
DirectionType ::= ENUMERATED
{
   toTarget,
   fromTarget,
   unknown
}
UserSignalType ::= CHOICE
{
    	copySignal        	BIT STRING,
   	 interpretedSignal 	INTEGER,
	cdcPdu    		CdcPdu
}
IRITransactionType ::= ENUMERATED
{
        iRIbegin,
        iRIcontinue,
        iRIend,
        iRIreport
}
LocationType ::= CHOICE
{
        geodeticData        BIT STRING,
        nameAddress         PrintableString (SIZE (1..100))
}
LIIDType ::= INTEGER (0..65535) -- 16 bit integer to identify interception
END
-- Source: ETSI TS 101 909-20-2 V1.2.1 (2006-03)
-- Annex A
TS101909202 {itu-t (0) identified-organization (4) etsi (0) ts101909 (1909) part20 (20) subpart2(2) interceptVersion (0)}
DEFINITIONS AUTOMATIC TAGS ::=
BEGIN
TARGETACTIVITYMONITOR ::= SEQUENCE
{
	version           INTEGER DEFAULT 1,   -- header, version -
  lIInstanceid         LIIdType,         -- header, who -
  timestamp          UTCTime,          -- header, when -
  targetLocation        LocationType,       -- header, where -
  direction          DirectionType,
  iRITransaction        IRITransactionType DEFAULT iRIreport,
  iRITransactionNumber     INTEGER,
  userSignal          UserSignalType,      -- Either copy or interpreted signalling
  cryptoCheckSum        BIT STRING         OPTIONAL
}
TTRAFFIC ::= SEQUENCE
{
	  version          INTEGER DEFAULT 1,   -- header, version -
    lIInstanceid       LIIdType,
    iRITransactionNumber   INTEGER,
    trafficPacket       BIT STRING,
    cryptoChecksum      BIT STRING  OPTIONAL
}
CTTRAFFIC ::= SEQUENCE
{
	  version          INTEGER DEFAULT 1,   -- header, version -
    lIInstanceid       LIIdType,
    correspondentCount    INTEGER,
    iRITransactionNumber   INTEGER,
    trafficPacket       BIT STRING,
    cryptoChecksum      BIT STRING  OPTIONAL
}
DirectionType ::= ENUMERATED
{
  toTarget,
  fromTarget,
  unknown
}
UserSignalType ::= CHOICE
{
  copySignal    BIT STRING,
  copyCharSignal  PrintableString,
  interpretedSignal INTEGER  -- Place holder
}
IRITransactionType ::= ENUMERATED
{
    iRIbegin,
    iRIcontinue,
    iRIend,
    iRIreport
}
LocationType ::= CHOICE
{
    geodeticData    BIT STRING,
    nameAddress     PrintableString (SIZE (1..100))
}
LIIdType ::= INTEGER (0..65535) -- 16 bit integer to identify interception
END




-- Source: ETSI TS 101 909-20-1 V1.1.2 (2005-10)
-- Annex A
PCESP  {iso(1) identified-organization(3) dod(6) internet(1) private(4) 
        enterprise(1) cable-Television-Laboratories-Inc(4491) clabProject(2) 
        clabProjPacketCable(2) pktcLawfulIntercept(5) pcesp(1) version-4(4)}
DEFINITIONS IMPLICIT TAGS ::=
BEGIN
ProtocolVersion ::= ENUMERATED { 
  -- Versions IO1 and IO2 do not support protocol versioning.
  v3(3),  -- Version supporting PacketCable Electronic Surveillance 
          -- Specification I03
  v4(4),  -- Version supporting PacketCable Electronic Surveillance 
          -- Specification I04 and PacketCable 1.5 Electronic Surveillance
          -- Specification I01
  ...}
CdcPdu ::= SEQUENCE {
  protocolVersion		[0] ProtocolVersion,
  message			[1] Message,
  ...
}
Message ::= CHOICE {
  answer                 [1]  Answer,
  ccclose                [2]  CCClose,
  ccopen                 [3]  CCOpen,
  reserved0              [4]  NULL,                -- Reserved
  origination            [5]  Origination,
  reserved1              [6]  NULL,                -- Reserved
  redirection            [7]  Redirection,
  release                [8]  Release,
  reserved2              [9]  NULL,                -- Reserved
  terminationattempt     [10] TerminationAttempt,
  reserved               [11] NULL,                -- Reserved
  ccchange               [12] CCChange,
  reserved3              [13] NULL,                -- Reserved
  reserved4              [14] NULL,                -- Reserved
  dialeddigitextraction  [15] DialedDigitExtraction,	
  networksignal          [16] NetworkSignal,
  subjectsignal          [17] SubjectSignal,
  mediareport            [18] MediaReport,
  serviceinstance        [19] ServiceInstance,
  confpartychange        [20] ConferencePartyChange,
  ...
}
Answer ::= SEQUENCE {
  caseId              [0] CaseId,
  accessingElementId  [1] AccessingElementId,
  eventTime           [2] EventTime,
  callId              [3] CallId,
  answering           [4] PartyId              OPTIONAL,
  ...
}
CCChange ::= SEQUENCE {
  caseId              [0] CaseId,
  accessingElementId  [1] AccessingElementId,
  eventTime           [2] EventTime,
  callId              [3] CallId,
  cCCId               [4] EXPLICIT CCCId,
  subject             [5] SDP                  OPTIONAL,
  associate           [6] SDP                  OPTIONAL,
  flowDirection       [7] FlowDirection,
  resourceState       [8] ResourceState        OPTIONAL,
  ...
}
CCClose ::= SEQUENCE {
  caseId              [0] CaseId,
  accessingElementId  [1] AccessingElementId,
  eventTime           [2] EventTime,
  cCCId               [3] EXPLICIT CCCId,
  flowDirection       [4] FlowDirection,
  ...
}
CCOpen ::= SEQUENCE {
  caseId              [0] CaseId,
  accessingElementId  [1] AccessingElementId,
  eventTime           [2] EventTime,
  ccOpenOption        CHOICE {
  ccOpenTime            [3] SEQUENCE OF CallId,
  reserved0             [4] NULL,               -- Reserved
  ...
                      },
  cCCId               [5] EXPLICIT CCCId,
  subject             [6] SDP                  OPTIONAL,
  associate           [7] SDP                  OPTIONAL,
  flowDirection       [8] FlowDirection,
  ...
}
ConferencePartyChange  ::= SEQUENCE {
  caseId             [0] CaseId,
  accessingElementId [1] AccessingElementId,
  eventTime          [2] EventTime,
  callId             [3] CallId,
  communicating      [4] SEQUENCE OF SEQUENCE {
                         -- include to identify parties participating in the 
                         -- communication.
    partyId [0] SEQUENCE OF PartyId OPTIONAL,
                -- identifies communicating party identities.
    cCCId   [1] EXPLICIT CCCId OPTIONAL,
                -- included when the content of the resulting call is
                -- delivered to identify the associated CCC(s).
    ...
                      } OPTIONAL,
  removed            [5] SEQUENCE OF SEQUENCE {
                       -- include to identify parties removed (e.g., hold
                       -- service) from the communication.
    partyId [0] SEQUENCE OF PartyId OPTIONAL,
                -- identifies removed party identity(ies).
    cCCId   [1] EXPLICIT CCCId OPTIONAL,
                -- included when the content of the resulting call is
                -- delivered to identify the associated CCC(s).
    ...
                      } OPTIONAL,
  joined             [6] SEQUENCE OF SEQUENCE{
                         -- include to identify parties newly added to the
                         -- communication.
    partyId [0] SEQUENCE OF PartyId OPTIONAL,
                -- identifies newly added party identity(ies) to an existing
                -- communication.
    cCCId   [1] EXPLICIT CCCId OPTIONAL,
                -- included when the content of the resulting call is
                -- delivered to identify the associated CCC(s).
    ...
                      } OPTIONAL,
  ...
}
DialedDigitExtraction ::= SEQUENCE {
  caseId              [0] CaseId,
  accessingElementId  [1] AccessingElementId,
  eventTime           [2] EventTime,
  callId              [3] CallId,
  digits              [4] VisibleString (SIZE (1..32, ...)),
                          -- string consisting of digits representing 
                          -- Dual Tone Multi Frequency (DTMF) tones 
                          -- having values from the following numbers,
                          -- letters, and symbols: 
                          -- "0", "1", "2", "3", "4", "5", "6", "7", 
                          -- "8", "9", "#", "*", "A", "B", "C", "D". 
                          -- Example: "123AB" or "*66" or "345#"
  ...
}
MediaReport ::= SEQUENCE {
  caseId              [0] CaseId,
  accessingElementId  [1] AccessingElementId,
  eventTime           [2] EventTime,
  callId              [3] CallId,
  subject             [4] SDP                  OPTIONAL,
  associate           [5] SDP                  OPTIONAL,
  ...
}
NetworkSignal ::= SEQUENCE {
  caseId              [0] CaseId,
  accessingElementId  [1] AccessingElementId,
  eventTime           [2] EventTime,
  callId              [3] CallId,
                      -- Signal
                      -- The following four parameters are used to report 
                      -- information regarding network-generated signals. 
                      -- Include at least one of the following four 
                      -- parameters to identify the network-generated signal 
                      -- being reported.
  alertingSignal       [4] AlertingSignal                        OPTIONAL,
  subjectAudibleSignal [5] AudibleSignal                         OPTIONAL,
  terminalDisplayInfo  [6] TerminalDisplayInfo                   OPTIONAL,
  other                [7] VisibleString (SIZE (1..128, ...))    OPTIONAL,
  -- Can be used to report undefined network signals
  signaledToPartyId    [8] PartyId,
  ...
}
Origination ::= SEQUENCE {
  caseId              [0] CaseId,
  accessingElementId  [1] AccessingElementId,
  eventTime           [2] EventTime,
  callId              [3] CallId,
  calling             [4] PartyId,
  called              [5] PartyId           OPTIONAL,
  input               CHOICE {
  userinput             [6] VisibleString  (SIZE (1..32, ...)),
  translationinput      [7] VisibleString  (SIZE (1..32, ...)),
  ...
                      },
  reserved0           [8] NULL,             -- Reserved
  transitCarrierId    [9] TransitCarrierId  OPTIONAL,
  ...
}
Redirection ::= SEQUENCE {
  caseId              [0] CaseId,
  accessingElementId  [1] AccessingElementId,
  eventTime           [2] EventTime,
  old                 [3] CallId,
  redirectedto        [4] PartyId,
  transitCarrierId    [5] TransitCarrierId     OPTIONAL,
  reserved0           [6] NULL,                -- Reserved
  reserved1           [7] NULL,                -- Reserved
  new                 [8] CallId               OPTIONAL,
  redirectedfrom      [9] PartyId              OPTIONAL,
  ...
}
Release ::= SEQUENCE {
  caseId             [0] CaseId,
  accessingElementId [1] AccessingElementId,
  eventTime          [2] EventTime,
  callId             [3] CallId,
  ...
}
ServiceInstance ::= SEQUENCE {
  caseId              [0] CaseId,
  accessingElementId  [1] AccessingElementId,
  eventTime           [2] EventTime,
  callId              [3] CallId,
  relatedCallId       [4] CallId               OPTIONAL,
  serviceName         [5] VisibleString (SIZE (1..128, ...)),
  firstCallCalling    [6] PartyId              OPTIONAL,
  secondCallCalling   [7] PartyId              OPTIONAL,
  called              [8] PartyId              OPTIONAL,
  calling             [9] PartyId              OPTIONAL,
  ...
}
SubjectSignal ::= SEQUENCE {
  caseId             [0] CaseId,
  accessingElementId [1] AccessingElementId,
  eventTime          [2] EventTime,
  callId             [3] CallId                OPTIONAL,
  signal             [4] SEQUENCE {
                     -- The following four parameters are used to report 
                     -- information regarding subject-initiated dialing and 
                     -- signaling. Include at least one of the following four 
                     -- parameters to identify the subject- initiated dialing 
                     -- and signaling information being reported.
  switchhookFlash            [0] VisibleString (SIZE (1..128, ...))  OPTIONAL,
  dialedDigits               [1] VisibleString (SIZE (1..128, ...))  OPTIONAL,
  featureKey                 [2] VisibleString (SIZE (1..128, ...))  OPTIONAL,
  otherSignalingInformation  [3] VisibleString (SIZE (1..128, ...))  OPTIONAL,
                      -- Can be used to report undefined subject signals
  ...
                        },
  signaledFromPartyId [5] PartyId,
  ...
}
TerminationAttempt ::= SEQUENCE {
  caseId               [0] CaseId,
  accessingElementId   [1] AccessingElementId,
  eventTime            [2] EventTime,
  callId               [3] CallId,
  calling              [4] PartyId             OPTIONAL,
  called               [5] PartyId             OPTIONAL,
  reserved0            [6] NULL,               -- Reserved
  redirectedFromInfo   [7] RedirectedFromInfo  OPTIONAL,
  ...
}
AccessingElementId ::= VisibleString (SIZE(1..15, ...))
                         --  Statically configured element number
AlertingSignal ::= ENUMERATED {
  notUsed               (0),   -- Reserved
  alertingPattern0      (1),   -- normal ringing
  alertingPattern1      (2),   -- distinctive ringing: intergroup
  alertingPattern2      (3),   -- distinctive ringing: special/priority 
  alertingPattern3      (4),   -- distinctive ringing: electronic key 
                               -- telephone srvc
  alertingPattern4      (5),   -- ringsplash, reminder ring
  callWaitingPattern1   (6),   -- normal call waiting tone
  callWaitingPattern2   (7),   -- incoming additional call waiting tone
  callWaitingPattern3   (8),   -- priority additional call waiting tone
  callWaitingPattern4   (9),   -- distinctive call waiting tone
  bargeInTone           (10),  -- barge-in tone (e.g. for operator barge-in)
  alertingPattern5      (11),  -- distinctive ringing: solution specific
  alertingPattern6      (12),  -- distinctive ringing: solution specific
  alertingPattern7      (13),  -- distinctive ringing: solution specific
  alertingPattern8      (14),  -- distinctive ringing: solution specific
  alertingPattern9      (15),  -- distinctive ringing: solution specific
  ...
}
-- This parameter identifies the type of alerting (ringing) signal that is 
-- applied toward the surveillance subject. See GR-506-CORE, LSSGR: Signaling 
-- for Analog Interfaces (A Module of the LATA Switching Systems Generic 
-- Requirements [LSSGR], FR-64).
AudibleSignal ::= ENUMERATED {
  notUsed                   (0),  -- Reserved
  dialTone                  (1),
  recallDialTone            (2),  -- recall dial tone, stutter dial tone 
  ringbackTone              (3),  -- tone indicates ringing at called party 
                                  -- end
  reorderTone               (4),  -- reorder tone, congestion tone
  busyTone                  (5),
  confirmationTone          (6),  -- tone confirms receipt and processing of 
                                  -- request
  expensiveRouteTone        (7),  -- tone indicates outgoing route is 
                                  -- expensive
  messageWaitingTone        (8),
  receiverOffHookTone       (9),  -- receiver off-hook tone, off-hook warning 
                                  -- tone
  specialInfoTone           (10), -- tone indicates call sent to announcement
  denialTone                (11), -- tone indicates denial of feature request
  interceptTone             (12), -- wireless intercept/mobile reorder tone
  answerTone                (13), -- wireless service tone
  tonesOff                  (14), -- wireless service tone
  pipTone                   (15), -- wireless service tone
  abbreviatedIntercept      (16), -- wireless service tone
  abbreviatedCongestion     (17), -- wireless service tone
  warningTone               (18), -- wireless service tone
  dialToneBurst             (19), -- wireless service tone
  numberUnObtainableTone    (20), -- wireless service tone
  authenticationFailureTone (21), -- wireless service tone
  ...
}
-- This parameter identifies the type of audible tone that is applied toward 
-- the surveillance subject. See GR-506-CORE, LSSGR: Signaling for Analog 
-- Interfaces (A Module of the LATA Switching Systems Generic Requirements 
-- [LSSGR], FR-64), ANSI/TIA/EIA-41-D, Cellular Radiotelecommunications 
-- Intersystem Operations, and GSM 02.40, Digital cellular telecommunications 
-- system (Phase 2+); Procedure for call progress indications.
CallId ::= SEQUENCE {
  sequencenumber  [0] VisibleString (SIZE(1..25, ...)),
  systemidentity  [1] VisibleString (SIZE(1..15, ...)),
  ...
}
-- The Delivery Function generates this structure from the
-- Billing-Correlation-ID (contained in the Event Messages).
-- The sequencenumber is generated by converting the
-- Timestamp (32 bits) and Event-Counter (32 bits) into 
-- ASCII strings, separating them with a comma.  
-- The systemidentity field is copied from the 
-- Element-ID field
CaseId ::= VisibleString (SIZE(1..25, ...))
CCCId ::= CHOICE {
  combCCC              [0] VisibleString (SIZE(1..20, ...)),
  sepCCCpair           [1] SEQUENCE{
  sepXmitCCC           [0] VisibleString (SIZE(1..20, ...)),
  sepRecvCCC           [1] VisibleString (SIZE(1..20, ...)),
  ...
                        },
  ...
}  
-- The Delivery Function MUST generate this structure
-- from the CCC-Identifier used for the corresponding
-- Call Content packet stream by converting the 32-bit
-- value into an 8-character (hex-encoded) ASCII string
-- consisting of digits 0-9 and letters A-F.
EventTime ::= GeneralizedTime
FlowDirection ::= ENUMERATED {
  downstream               (1), 
  upstream                 (2), 
  downstream-and-upstream  (3),
  ...
}
PartyId ::= SEQUENCE {
  reserved0            [0]  NULL               OPTIONAL, -- Reserved
  reserved1            [1]  NULL               OPTIONAL, -- Reserved
  reserved2            [2]  NULL               OPTIONAL, -- Reserved
  reserved3            [3]  NULL               OPTIONAL, -- Reserved
  reserved4            [4]  NULL               OPTIONAL, -- Reserved
  reserved5            [5]  NULL               OPTIONAL, -- Reserved
  dn                   [6]  VisibleString (SIZE(1..15, ...))  OPTIONAL,
  userProvided         [7]  VisibleString (SIZE(1..15, ...))  OPTIONAL,
  reserved6            [8]  NULL               OPTIONAL, -- Reserved
  reserved7            [9]  NULL               OPTIONAL, -- Reserved
  ipAddress            [10] VisibleString (SIZE(1..32, ...))  OPTIONAL,
  reserved8            [11] NULL               OPTIONAL, -- Reserved
  trunkId              [12] VisibleString (SIZE(1..32, ...))  OPTIONAL,
  reserved9            [13] NULL               OPTIONAL, -- Reserved
  genericAddress       [14] VisibleString (SIZE(1..32, ...))  OPTIONAL,
  genericDigits        [15] VisibleString (SIZE(1..32, ...))  OPTIONAL,
  genericName          [16] VisibleString (SIZE(1..48, ...))  OPTIONAL,
  port                 [17] VisibleString (SIZE(1..32, ...))  OPTIONAL,
  context              [18] VisibleString (SIZE(1..32, ...))  OPTIONAL,
  ...
}
RedirectedFromInfo ::= SEQUENCE {
  lastRedirecting        [0] PartyId           OPTIONAL,
  originalCalled         [1] PartyId           OPTIONAL,
  numRedirections        [2] INTEGER (1..100, ...)  OPTIONAL,
  ...
}
ResourceState ::= ENUMERATED {reserved(1), committed(2), ...}
SDP ::= UTF8String
-- The format and syntax of this field are defined in [8].
TerminalDisplayInfo ::= SEQUENCE {
  generalDisplay         [0] VisibleString (SIZE (1..80, ...))  OPTIONAL,
    -- Can be used to report display-related
    -- network signals not addressed by
    -- other parameters.
  calledNumber           [1] VisibleString (SIZE (1..40, ...))  OPTIONAL,
  callingNumber          [2] VisibleString (SIZE (1..40, ...))  OPTIONAL,
  callingName            [3] VisibleString (SIZE (1..40, ...))  OPTIONAL,
  originalCalledNumber   [4] VisibleString (SIZE (1..40, ...))  OPTIONAL,
  lastRedirectingNumber  [5] VisibleString (SIZE (1..40, ...))  OPTIONAL,
  redirectingName        [6] VisibleString (SIZE (1..40, ...))  OPTIONAL,
  redirectingReason      [7] VisibleString (SIZE (1..40, ...))  OPTIONAL,
  messageWaitingNotif    [8] VisibleString (SIZE (1..40, ...))  OPTIONAL,
  ...
}
-- This parameter reports information that is displayed on the surveillance 
-- subject's terminal. See GR-506-CORE, LSSGR: Signaling for Analog 
-- Interfaces (A Module of the LATA Switching Systems Generic Requirements 
-- [LSSGR], FR-64).
TransitCarrierId ::= VisibleString (SIZE(3..7, ...))
END -- PCESP




-- Source: 06132v203_C01_ASN1.asn 
-- ETSI EN 301 040 V2.1.1 (2006-03)
EN301040 {itu-t (0) identified-organization (4) etsi (0) en301040 (1040) interceptVersion (0)}
DEFINITIONS AUTOMATIC TAGS ::=
BEGIN
LIACTIVATEreq ::= SEQUENCE
{
    	timeStamp    		UTCTime,
	invokeId		INTEGER,
	targetAddress   	AddressType,
    	expiryDateTime		UTCTime,
    	targetname   		VisibleString 		OPTIONAL,
    	additionaltargetdata	VisibleString 		OPTIONAL,
    	monitorServiceList   	SEQUENCE OF ActivityType
}
LIACTIVATEconf ::= SEQUENCE
{
    	timeStamp    		UTCTime,
	invokeId		INTEGER,
	result			BOOLEAN,
    	tLIInstanceid    	TLIIdType   		OPTIONAL	-- Conditional on value of Result --
}
LIMODIFYreq ::= SEQUENCE
{
    	tLIInstanceid           TLIIdType,
    	timestamp               UTCTime,
    	modificationNumber	INTEGER,
	modificationType	CHOICE
	{
		halt			BOOLEAN,
		reset			BOOLEAN,
    		expiryDateTime   	UTCTime,
    		targetname   		VisibleString,
    		additionaltargetdata   	VisibleString,
    		monitorServiceList   	SEQUENCE OF ActivityType
	}
}
LIMODIFYconf ::= SEQUENCE
{
    	tLIInstanceid           TLIIdType,
    	timestamp		UTCTime,
    	modificationNumber	INTEGER,
    	result			BOOLEAN
}
LISTATUSind ::= SEQUENCE
{
    	tLIInstanceid           TLIIdType,
    	timestamp               UTCTime,
    	tETRASysStatus  	StatusType
}
TARGETACTIVITYMONITORind ::= SEQUENCE
{
    	tLIInstanceid    	TLIIdType,  			-- header, who -
    	timestamp    		UTCTime,   			-- header, when -
    	targetLocation    	LocationType,   		-- header, where -
    	targetAction   		ActivityType,
    	supplementaryTargetaddress  	AddressType   			OPTIONAL,
    	cotargetaddress  		SEQUENCE OF AddressType  	OPTIONAL,
    	cotargetlocation  		SEQUENCE OF LocationType  	OPTIONAL
}
TARGETCOMMSMONITORind ::= SEQUENCE
{
    	tLIInstanceid    		TLIIdType,
    	timestamp    			UTCTime,
    	targetlocation   		LocationType,
    	supplementaryTargetaddress  	AddressType OPTIONAL,
    	targetcommsid   		CircuitIdType,
    	cotargetaddress   		SEQUENCE OF AddressType 	OPTIONAL,
    	cotargetcommsid  		SEQUENCE OF CircuitIdType 	OPTIONAL
}
TTRAFFICind ::= SEQUENCE
{
    	tLIInstanceid    			TLIIdType,
	trafficPacket				BIT STRING
}
CTTRAFFICind ::= SEQUENCE
{
    	tLIInstanceid    			TLIIdType,
	trafficPacket				BIT STRING
}
ActivityClassType ::= ENUMERATED
{
	allServices,
	tETRASpeech,
	singleSlotData24,
	singleSlotData48,
	singleSlotData72,
	multiSlotData224,
	multiSlotData248,
	multiSlotData272,
	multiSlotData324,
	multiSlotData348,
	multiSlotData372,
	multiSlotData424,
	multiSlotData448,
	multiSlotData472,
	sDSType1,
	sDSType2,
	sDSType3,
	sDSType4,
	status,
	sDSACKType1,
	sDSACKType2,
	sDSACKType3,
	sDSACKType4,
	statusack,
	sDSAcknowledgementsuccess,
	sDSAcknowledgementfail,
	sCLNSPacketData,
	cONSPacketData,
	internetProtocol,
	swMIauthenticationsuccess,
	swMIauthenticationfail,
	iTSIauthenticationsuccess,
	iTSIauthenticationfail,
	oTARSCKsuccess,
	oTARSCKfail,
	oTARGCKsuccess,
	oTARGCKfail,
	oTARCCKsuccess,
	oTARCCKfail,
	tARGETSUSCRIPTIONDISABLEDT,
	tARGETEQUIPMENTDISABLEDT,
	tARGETSUSCRIPTIONDISABLEDP,
	tARGETEQUIPEMENTDISABLEDP,
	tARGETSUBSCRIPTIONENABLED,
	tARGETEQUIPMENTENABLED,
	sessionregistration,
	sessionderegistration,
	mIGRATION,
	rOAMING, 
	supplementaryService
}
ActivityType::= SEQUENCE
{
	cctivity	ActivityClassType,
	callRelation	ENUMERATED
	{
		begin,
		end,
		continue,
		report
	},
	direction	ENUMERATED 
	{
		toTarget,
		fromTarget
 	} OPTIONAL, 
	scope		ENUMERATED
	{
		point2Point,
		point2MultiPoint,
		broadcast
	} OPTIONAL,
	cPlaneData	BIT STRING OPTIONAL,
	sStype		SSType OPTIONAL
}
AddressType ::= SEQUENCE
{
	tSI			TSIType,
	supplementaryAddress	SEQUENCE OF TETRAAddressType OPTIONAL
}
TETRAAddressType ::= CHOICE
{
	tETRAaddress	TSIType,
	pISNaddress	NumericString (SIZE (20)),
	iP4address	BIT STRING (SIZE (32)), 	-- 32 bits -
	iP6address	BIT STRING (SIZE (128)),	-- 128 bits -
	e164address	NumericString (SIZE (20)),
	tEI		TEIType
}
CellIdType ::= BIT STRING (SIZE (16)) 	-- 16 bits -
LocationAreaType ::= BIT STRING (SIZE (14)) -- 14 bits, as defined in ETS 300 392-2 -
LocationType ::= CHOICE
{
	mSLoc		TETRACGIType,
	lSLoc		TETRAAddressType
}
MCCType ::= BIT STRING (SIZE (10)) 	-- 10 bits, as defined in ETS 300 392-1 -
MNCType ::= BIT STRING (SIZE (14)) 	-- 14 bits, as defined in ETS 300 392-1 -
SSIType ::= BIT STRING (SIZE (24)) 	-- 24 bits, as defined in ETS 300 392-1 -
CircuitIdType ::= NumericString (SIZE (20))
SSType ::= ENUMERATED
{
	ambienceListening,
	adviceofCharge,
	accessPriority,
	areaSelection,
	barringofIncomingCalls,
	barringofOutgoingCalls,
	callAuthorizedbyDispatcher,
	callCompletiontoBusySubscriber,
	callCompletiononNoReply,
	callForwardingonBusy,
	callForwardingonNoReply,
	callForwardingonNotReachable,
	callForwardingUnconditional,
	callingLineIdentificationPresentation,
	callingConnectedLineIdentificationRestriction,
	connectedLineIdentificationPresentation,
    	callReport,
    	callRetention,
    	callWaiting,
    	dynamicGroupNumberAssignment,
    	discreetListening,
    	callHold,
    	includeCall,
    	lateEntry,
    	listSearchCall,
    	priorityCall,
    	preemptivePriorityCall,
    	shortNumberAddressing,
    	transferofControl,
    	talkingPartyIdentification
}
StatusType ::= ENUMERATED
{
	networkFullyAvailable,
	networkErrorsAffectingIntercept,
	reconfigurationInProgress,
	sessionExpired,
	gatewayServicesUnavailable
}
TETRACGIType ::= SEQUENCE
{
	mcc	MCCType,
	mnc	MNCType,
	lai	LocationAreaType,
	cI	CellIdType	OPTIONAL
}
TLIIdType ::= BIT STRING (SIZE (16)) 	-- 16 bits -
TSIType ::= SEQUENCE
{
    	mcc       MCCType,
    	mnc       MNCType,
    	ssi       SSIType
}
TEIType ::= BIT STRING (SIZE (60)) -- 60 bits, as defined in ETS 300 392-1 -
END  -- EN301040




-- Source: Module Remote-Operations-Information-Objects (X.880:07/1994)
-- See also ITU-T X.880 (1994) Technical Cor. 1 (07/1995)
-- See also the index of all ASN.1 assignments needed in this Recommendation
Remote-Operations-Information-Objects {joint-iso-itu-t remote-operations(4) informationObjects(5) version1(0)} 
DEFINITIONS ::=
BEGIN
-- exports everything
IMPORTS
  emptyBind, emptyUnbind
    FROM Remote-Operations-Useful-Definitions {joint-iso-itu-t
      remote-operations(4) useful-definitions(7) version1(0)};
OPERATION ::= CLASS {
  &ArgumentType          OPTIONAL,
  &argumentTypeOptional  BOOLEAN OPTIONAL,
  &returnResult          BOOLEAN DEFAULT TRUE,
  &ResultType            OPTIONAL,
  &resultTypeOptional    BOOLEAN OPTIONAL,
  &Errors                ERROR OPTIONAL,
  &Linked                OPERATION OPTIONAL,
  &synchronous           BOOLEAN DEFAULT FALSE,
  &alwaysReturns         BOOLEAN DEFAULT TRUE,
  &InvokePriority        Priority OPTIONAL,
  &ResultPriority        Priority OPTIONAL,
  &operationCode         Code UNIQUE OPTIONAL
}
WITH SYNTAX {
  [ARGUMENT &ArgumentType
   [OPTIONAL &argumentTypeOptional]]
  [RESULT &ResultType
   [OPTIONAL &resultTypeOptional]]
  [RETURN RESULT &returnResult]
  [ERRORS &Errors]
  [LINKED &Linked]
  [SYNCHRONOUS &synchronous]
  [ALWAYS RESPONDS &alwaysReturns]
  [INVOKE PRIORITY &InvokePriority]
  [RESULT-PRIORITY &ResultPriority]
  [CODE &operationCode]
}
ERROR ::= CLASS {
  &ParameterType          OPTIONAL,
  &parameterTypeOptional  BOOLEAN OPTIONAL,
  &ErrorPriority          Priority OPTIONAL,
  &errorCode              Code UNIQUE OPTIONAL
}
WITH SYNTAX {
  [PARAMETER &ParameterType
   [OPTIONAL &parameterTypeOptional]]
  [PRIORITY &ErrorPriority]
  [CODE &errorCode]
}
OPERATION-PACKAGE ::= CLASS {
  &Both      OPERATION OPTIONAL,
  &Consumer  OPERATION OPTIONAL,
  &Supplier  OPERATION OPTIONAL,
  &id        OBJECT IDENTIFIER UNIQUE OPTIONAL
}
-- continued on the next page
WITH SYNTAX {
  [OPERATIONS &Both]
  [CONSUMER INVOKES &Supplier]
  [SUPPLIER INVOKES &Consumer]
  [ID &id]
}
CONNECTION-PACKAGE ::= CLASS {
  &bind                OPERATION DEFAULT emptyBind,
  &unbind              OPERATION DEFAULT emptyUnbind,
  &responderCanUnbind  BOOLEAN DEFAULT FALSE,
  &unbindCanFail       BOOLEAN DEFAULT FALSE,
  &id                  OBJECT IDENTIFIER UNIQUE OPTIONAL
}
WITH SYNTAX {
  [BIND &bind]
  [UNBIND &unbind]
  [RESPONDER UNBIND &responderCanUnbind]
  [FAILURE TO UNBIND &unbindCanFail]
  [ID &id]
}
CONTRACT ::= CLASS {
  &connection           CONNECTION-PACKAGE OPTIONAL,
  &OperationsOf         OPERATION-PACKAGE OPTIONAL,
  &InitiatorConsumerOf  OPERATION-PACKAGE OPTIONAL,
  &InitiatorSupplierOf  OPERATION-PACKAGE OPTIONAL,
  &id                   OBJECT IDENTIFIER UNIQUE OPTIONAL
}
WITH SYNTAX {
  [CONNECTION &connection]
  [OPERATIONS OF &OperationsOf]
  [INITIATOR CONSUMER OF &InitiatorConsumerOf]
  [RESPONDER CONSUMER OF &InitiatorSupplierOf]
  [ID &id]
}
ROS-OBJECT-CLASS ::= CLASS {
  &Is                    ROS-OBJECT-CLASS OPTIONAL,
  &Initiates             CONTRACT OPTIONAL,
  &Responds              CONTRACT OPTIONAL,
  &InitiatesAndResponds  CONTRACT OPTIONAL,
  &id                    OBJECT IDENTIFIER UNIQUE
}
WITH SYNTAX {
  [IS &Is]
  [BOTH &InitiatesAndResponds]
  [INITIATES &Initiates]
  [RESPONDS &Responds]
  ID &id
}
Code ::= CHOICE {local   INTEGER,
                 global  OBJECT IDENTIFIER
}
Priority ::= INTEGER(0..MAX)
END -- end of Information Object specifications




-- Source: Module Remote-Operations-Useful-Definitions (X.880:07/1994)
-- See also ITU-T X.880 (1994) Technical Cor. 1 (07/1995)
-- See also the index of all ASN.1 assignments needed in this Recommendation
Remote-Operations-Useful-Definitions {joint-iso-itu-t remote-operations(4) useful-definitions(7) version1(0)} 
DEFINITIONS IMPLICIT TAGS ::=
BEGIN
-- exports everything
IMPORTS
  OPERATION, ERROR, OPERATION-PACKAGE, Code
    FROM Remote-Operations-Information-Objects {joint-iso-itu-t
      remote-operations(4) informationObjects(5) version1(0)}
  InvokeId, ROS{}
    FROM Remote-Operations-Generic-ROS-PDUs {joint-iso-itu-t
      remote-operations(4) generic-ROS-PDUs(6) version1(0)};
emptyBind OPERATION ::= {ERRORS       {refuse}
                         SYNCHRONOUS  TRUE
}
emptyUnbind OPERATION ::= {SYNCHRONOUS  TRUE
}
refuse ERROR ::= {CODE  local:-1
}
no-op OPERATION ::= {ALWAYS RESPONDS  FALSE
                     CODE             local:-1
}
/* 
-- Start of deletion to enable successful compilation
Forward{OPERATION:OperationSet} OPERATION ::=
  {OperationSet | OperationSet.&Linked.&Linked |
   OperationSet.&Linked.&Linked.&Linked.&Linked}
Reverse{OPERATION:OperationSet} OPERATION ::=
  {Forward{{OperationSet.&Linked}}}
ConsumerPerforms{OPERATION-PACKAGE:package} OPERATION ::=
  {Forward{{package.&Consumer}} | Forward{{package.&Both}} |
   Reverse{{package.&Supplier}} | Reverse{{package.&Both}}}
SupplierPerforms{OPERATION-PACKAGE:package} OPERATION ::=
  {Forward{{package.&Supplier}} | Forward{{package.&Both}} |
   Reverse{{package.&Consumer}} | Reverse{{package.&Both}}}
AllOperations{OPERATION-PACKAGE:package} OPERATION ::=
  {ConsumerPerforms{package} | SupplierPerforms{package}}
-- End of deletion to enable successful compilation
*/
-- continued on the next page
recode{OPERATION:operation, Code:code} OPERATION ::= {
  ARGUMENT         operation.&ArgumentType
  OPTIONAL         operation.&argumentTypeOptional
  RESULT           operation.&ResultType
  OPTIONAL         operation.&resultTypeOptional
  RETURN RESULT    operation.&returnResult
  ERRORS           {operation.&Errors}
  LINKED           {operation.&Linked}
  SYNCHRONOUS      operation.&synchronous
  ALWAYS RESPONDS  operation.&alwaysReturns
  INVOKE PRIORITY  {operation.&InvokePriority}
  RESULT-PRIORITY  {operation.&ResultPriority}
  CODE             code
}
switch{OPERATION-PACKAGE:package, OBJECT IDENTIFIER:id} OPERATION-PACKAGE ::= 
{
  OPERATIONS        {package.&Both}
  CONSUMER INVOKES  {package.&Consumer}
  SUPPLIER INVOKES  {package.&Supplier}
  ID                id
}
combine{OPERATION-PACKAGE:ConsumerConsumes, OPERATION-PACKAGE:ConsumerSupplies,
        OPERATION-PACKAGE:base} OPERATION-PACKAGE ::= {
  OPERATIONS        {ConsumerConsumes.&Both | ConsumerSupplies.&Both}
  CONSUMER INVOKES
    {ConsumerConsumes.&Consumer | ConsumerSupplies.&Supplier}
  SUPPLIER INVOKES
    {ConsumerConsumes.&Supplier | ConsumerSupplies.&Consumer}
  ID                base.&id
}
-- 
-- Disabled - Australian customisation
-- 
-- ROS-SingleAS{InvokeId:InvokeIdSet, OPERATION-PACKAGE:package} ::=
--  ROS{{InvokeIdSet}, {AllOperations  {package}}, {AllOperations  {package}}}
-- ROS-ConsumerAS{InvokeId:InvokeIdSet, OPERATION-PACKAGE:package} ::=
--  ROS
--    {{InvokeIdSet}, {ConsumerPerforms  {package}},
--    {SupplierPerforms  {package}}}
-- ROS-SupplierAS{InvokeId:InvokeIdSet, OPERATION-PACKAGE:package} ::=
--  ROS
--    {{InvokeIdSet}, {SupplierPerforms  {package}},
--    {ConsumerPerforms  {package}}}
END -- end of useful definitions.




-- Source: Module Remote-Operations-Generic-ROS-PDUs (X.880:07/1994)
-- See also ITU-T X.880 (1994) Technical Cor. 1 (07/1995)
-- See also the index of all ASN.1 assignments needed in this Recommendation
Remote-Operations-Generic-ROS-PDUs {joint-iso-itu-t remote-operations(4) generic-ROS-PDUs(6) version1(0)} 
DEFINITIONS IMPLICIT TAGS ::=
BEGIN
-- exports everything
IMPORTS
  OPERATION, ERROR
    FROM Remote-Operations-Information-Objects {joint-iso-itu-t
      remote-operations(4) informationObjects(5) version1(0)};
ROS{InvokeId:InvokeIdSet, OPERATION:Invokable, OPERATION:Returnable} ::=
  CHOICE {
  invoke        [1]  Invoke{{InvokeIdSet}, {Invokable}},
  returnResult  [2]  ReturnResult{{Returnable}},
  returnError   [3]  ReturnError{{Errors  {--!--{Returnable}}}},
  reject        [4]  Reject
}
(CONSTRAINED BY { -- must conform to the above definition --} !
 RejectProblem:general-unrecognizedPDU)
Invoke{InvokeId:InvokeIdSet, OPERATION:Operations} ::= SEQUENCE {
  invokeId
    InvokeId(InvokeIdSet)
      (CONSTRAINED BY { -- must be unambiguous --} !
       RejectProblem:invoke-duplicateInvocation),
  linkedId
    CHOICE {present  [0] IMPLICIT present < InvokeId,
            absent   [1] IMPLICIT NULL
  }
  (CONSTRAINED BY { -- must identify an outstanding operation --} !
   RejectProblem:invoke-unrecognizedLinkedId)
  (CONSTRAINED BY { -- which has one or more linked operations--} !
   RejectProblem:invoke-linkedResponseUnexpected) OPTIONAL,
  opcode
    OPERATION.&operationCode
      ({Operations} !RejectProblem:invoke-unrecognizedOperation),
  argument
    OPERATION.&ArgumentType
      ({Operations}{@opcode} !RejectProblem:invoke-mistypedArgument) OPTIONAL
}
(CONSTRAINED BY { -- must conform to the above definition --} !
 RejectProblem:general-mistypedPDU)
(WITH COMPONENTS {
   ...,
   linkedId  ABSENT
 } |
 WITH COMPONENTS {
   ...,
   linkedId  PRESENT,
   opcode    (CONSTRAINED BY { -- must be in the &Linked field of the associated operation --
                } !RejectProblem:invoke-unexpectedLinkedOperation)
 })
-- continued on the next page
ReturnResult{OPERATION:Operations} ::= SEQUENCE {
  invokeId
    InvokeId
      (CONSTRAINED BY { -- must be that for an outstanding operation --} !
       RejectProblem:returnResult-unrecognizedInvocation)
      (CONSTRAINED BY { -- which returns a result --} !
       RejectProblem:returnResult-resultResponseUnexpected),
  result
    SEQUENCE {opcode
                OPERATION.&operationCode({Operations})
                  (CONSTRAINED BY { -- identified by invokeId --} !
                   RejectProblem:returnResult-unrecognizedInvocation),
              result
                OPERATION.&ResultType
                  ({Operations}{@.opcode} !
                   RejectProblem:returnResult-mistypedResult)} OPTIONAL
}
(CONSTRAINED BY { -- must conform to the above definition --} !
 RejectProblem:general-mistypedPDU)
ReturnError{ERROR:Errors} ::= SEQUENCE {
  invokeId
    InvokeId
      (CONSTRAINED BY { -- must be that for an outstanding operation --} !
       RejectProblem:returnError-unrecognizedInvocation)
      (CONSTRAINED BY { -- which returns an error --} !
       RejectProblem:returnError-errorResponseUnexpected),
  errcode
    ERROR.&errorCode({Errors} !RejectProblem:returnError-unrecognizedError)
      (CONSTRAINED BY { -- must be in the &Errors field of the associated operation --
         } !RejectProblem:returnError-unexpectedError),
  parameter
    ERROR.&ParameterType
      ({Errors}{@errcode} !RejectProblem:returnError-mistypedParameter)
      OPTIONAL
}
(CONSTRAINED BY { -- must conform to the above definition --} !
 RejectProblem:general-mistypedPDU)
Reject ::= SEQUENCE {
  invokeId  InvokeId,
  problem
    CHOICE {general       [0]  GeneralProblem,
            invoke        [1]  InvokeProblem,
            returnResult  [2]  ReturnResultProblem,
            returnError   [3]  ReturnErrorProblem}
}
(CONSTRAINED BY { -- must conform to the above definition --} !
 RejectProblem:general-mistypedPDU)
GeneralProblem ::= INTEGER {
  unrecognizedPDU(0), mistypedPDU(1), badlyStructuredPDU(2)}
-- continued on the next page
InvokeProblem ::= INTEGER {
  duplicateInvocation(0), unrecognizedOperation(1), mistypedArgument(2),
  resourceLimitation(3), releaseInProgress(4), unrecognizedLinkedId(5),
  linkedResponseUnexpected(6), unexpectedLinkedOperation(7)}
ReturnResultProblem ::= INTEGER {
  unrecognizedInvocation(0), resultResponseUnexpected(1), mistypedResult(2)
}
ReturnErrorProblem ::= INTEGER {
  unrecognizedInvocation(0), errorResponseUnexpected(1), unrecognizedError(2),
  unexpectedError(3), mistypedParameter(4)}
RejectProblem ::= INTEGER {
  general-unrecognizedPDU(0), general-mistypedPDU(1),
  general-badlyStructuredPDU(2), invoke-duplicateInvocation(10),
  invoke-unrecognizedOperation(11), invoke-mistypedArgument(12),
  invoke-resourceLimitation(13), invoke-releaseInProgress(14),
  invoke-unrecognizedLinkedId(15), invoke-linkedResponseUnexpected(16),
  invoke-unexpectedLinkedOperation(17),
  returnResult-unrecognizedInvocation(20),
  returnResult-resultResponseUnexpected(21), returnResult-mistypedResult(22),
  returnError-unrecognizedInvocation(30),
  returnError-errorResponseUnexpected(31), returnError-unrecognizedError(32),
  returnError-unexpectedError(33), returnError-mistypedParameter(34)}
InvokeId ::= CHOICE {present  INTEGER,
                     absent   NULL
}
noInvokeId InvokeId ::= absent:NULL
NoInvokeId InvokeId ::= {noInvokeId}
Errors{OPERATION:Operations} ERROR ::= {Operations.&Errors}
-- continued on the next page
Bind{OPERATION:operation} ::= CHOICE {
  bind-invoke  [16]  OPERATION.&ArgumentType({operation}),
  bind-result  [17]  OPERATION.&ResultType({operation}),
  bind-error   [18]  OPERATION.&Errors.&ParameterType({operation})
}
Unbind{OPERATION:operation} ::= CHOICE {
  unbind-invoke  [19]  OPERATION.&ArgumentType({operation}),
  unbind-result  [20]  OPERATION.&ResultType({operation}),
  unbind-error   [21]  OPERATION.&Errors.&ParameterType({operation})
}
END -- end of generic ROS PDU definitions
