Test-Protocol
{ joint-iso-itu-t internationalRA(23) set(42) set-vendors(9) example(99) modules(2) people(2) }

DEFINITIONS IMPLICIT TAGS ::=
BEGIN
IMPORTS
;

Human ::= SEQUENCE
{
    payload [0] Payload
}

Payload ::= SEQUENCE
{
    name [0] UTF8String,
    iRIsContent   [1] IRIsContent   
}

IRIsContent ::= CHOICE
{
    typeA    TypeA,
    --sofA   SofA,
    typeB TypeB,
    int    INTEGER
}

SofA ::= SEQUENCE OF TypeA

TypeA ::= CHOICE
{
   start [1] TypeB,
   mid   [2] TypeB,
   end   [3] TypeB
   
}

TypeB ::= SEQUENCE
{
  stuff [0] UTF8String,
  other [1] INTEGER
}


END
